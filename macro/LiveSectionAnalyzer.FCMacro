"""LiveSectionAnalyzer.FCMacro

Interactive, real-time section analysis for FreeCAD.
Select a solid, run the macro, and move the section plane with a slider,
a spin box or by dragging a gizmo directly in the 3D view.

Version: 0.8.1   (keep in sync with VERSION below)
Author: Sedat Kuran
License: MIT (see LICENSE)
Repository: https://github.com/sedatkrn/FreeCAD-LiveSectionAnalyzer
Copyright (c) 2026 Sedat Kuran

This file is generated from src/ by tools/build_macro.py; edit the files there.
"""

import FreeCAD as App
import FreeCADGui as Gui
import Part
import math
import time

from PySide.QtWidgets import (
    QColorDialog, QDockWidget, QDoubleSpinBox, QMessageBox, QLabel, QCheckBox,
    QComboBox, QPushButton, QSlider, QSpinBox, QWidget,
    QHBoxLayout, QVBoxLayout, QScrollArea, QToolButton, QFrame,
    QDialogButtonBox, QSizePolicy, QListWidget, QListWidgetItem, QApplication, QProgressDialog,
)

from PySide.QtGui import QIcon, QPixmap, QColor

from PySide.QtCore import Qt, QTimer, QObject, QEvent

try:
    import numpy as np
    HAS_NP = True
except Exception:
    np = None
    HAS_NP = False

try:
    from pivy import coin
    HAS_COIN = True
except Exception:
    coin = None
    HAS_COIN = False

# Where the options panel lives:
#   "dock" -> its own dockable / floating window (the Tasks panel stays free, so measuring
#             and other task dialogs work while the section is open)
#   "task" -> FreeCAD's Tasks panel (Combo View)
# "task" falls back to "dock" automatically when another task dialog is open.
PANEL_MODE = "dock"

# Side of the main window the dock opens on ("left" or "right"); drag it anywhere afterwards,
# or float it by double-clicking its title.
DOCK_AREA = "right"

# Width the dock opens with, in pixels; it can be dragged wider afterwards.
PANEL_WIDTH = 315

# If the wrong half of the object is clipped away, flip this value.
CLIP_KEEP_NEGATIVE = True

# Safety limit for the number of hatch lines generated per update.
MAX_HATCH_LINES = 1500

# Let the gizmo be grabbed on the plane itself (surface and outline), not only
# on the arrow. Off by default: the plane covers the model on screen, and while
# it grabs clicks you cannot select faces under it (e.g. for Assembly joints).
GIZMO_PICK_PLANE = False

# The gizmo arrow and rotation handles keep this size on screen (half the arrow
# length, in pixels) while you zoom; the plane outline still follows the model.
# 0 = everything scales with the model, as before 0.7.
GIZMO_SCREEN_PX = 110

# Follow parts that move (Assembly solver, dragging, placement edits). After the
# last change the fine section is rebuilt once the scene has been still this long.
FOLLOW_SCENE = True
SCENE_SETTLE_MS = 300

# v0.5 (experimental): print per-update timings (slice / faces / fill / edges /
# hatch / total, objects skipped by the bounding-box test) to the Report view.
DEBUG_TIMING = True

# v0.5 (experimental): while the plane is being dragged, objects whose exact slice
# took longer than this many ms are shown as a fast outline computed from their
# tessellation (numpy). The exact section is computed when the drag ends.
FAST_PREVIEW_MS = 60

# Max cached slices (all objects together).
SLICE_CACHE_SIZE = 256

# With nothing selected, scenes up to this many visible solids are sectioned
# completely; bigger scenes start with nothing checked.
AUTO_SECTION_MAX_OBJECTS = 12

# The section fill / edges / hatch lie exactly in the clip plane. They are
# nudged by this fraction of the model size so the clip does not cut them.
OVERLAY_OFFSET_REL = 1e-4

# v0.5 (experimental): build contour, hatch and fill from the tessellation instead of
# OpenCascade. This is only the start state of the "Mesh-based section" checkbox in the
# panel; the exact path stays available for comparison and is always used by Freeze.
# Curves look polygonal at a coarse tolerance.
MESH_SECTION = True

# Tessellation tolerance as a fraction of the object's bounding-box diagonal: coarse while
# the plane is being dragged, fine once it rests.
MESH_TOL_REL = 1e-3
MESH_TOL_FINE_REL = 1e-4

# Draw hatch and fill while dragging too (mesh section only). Turn off if a huge
# assembly stutters.
MESH_DRAG_HATCH = True

# Hatch style per sectioned object (exact and mesh section alike): (angle in degrees,
# spacing factor). Neighbouring parts get different entries, so touching sections can be
# told apart. One entry, e.g. ((45.0, 1.0),), hatches everything the same way.
HATCH_STYLES = ((45.0, 1.0), (135.0, 1.0), (0.0, 1.5), (90.0, 1.5))

# Max cached mesh sections (all objects together).
MESH_CACHE_SIZE = 128
# Safety limits (the first tick of "Mesh-based section" tessellates every checked object)
MESH_FINE_MAX_TRIS = 8000       # fine mesh only when the coarse one has at most this many triangles
MESH_TOL_MIN = 0.01             # mm, tessellation tolerance never goes below this (threads!)
MESH_FINE_PREDICT = 25.0        # fine mesh costs ~this times the coarse one; skipped if it would exceed the budget
MESH_MAX_FILL_POINTS = 40000    # no fill polygons for sections with more loop points than this
MESH_FINE_BUDGET_S = 1.5        # per update: no further fine tessellations after this much time


# ----------------------------------------------------------------------
# Mesh section core: pure numpy, no FreeCAD (tests/test_mesh_core.py runs it alone)
# ----------------------------------------------------------------------
# BEGIN MESH CORE
MESH_MAX_QUAD_POINTS = 20000    # convex-quad fill up to this many loop points
MESH_INDEX_MIN_TRIS = 2000      # smaller meshes are simply scanned for every plane position
MESH_MAX_HOLES = 400            # more holes per outer loop: no keyhole bridging (fill skipped)
def mesh_weld(V, T, sid, tol):
    """Merge coincident vertices of a tessellation.

    OpenCascade duplicates the vertices along face borders; welding them makes the mesh
    edges shared, so the section contour can be chained by edge id. Points are clustered
    by gaps along x, then y, then z (no grid, so nothing is split at a cell border).
    sid: solid id per vertex, so touching solids stay separate.
    Returns (V, T) with degenerate triangles removed.
    """
    n = len(V)
    if n == 0:
        return V, T
    gid = np.asarray(sid, dtype=np.int64)
    for ax in range(3):
        order = np.lexsort((V[:, ax], gid))
        g, x = gid[order], V[order, ax]
        brk = np.ones(n, dtype=bool)
        brk[1:] = (g[1:] != g[:-1]) | (x[1:] - x[:-1] > tol)
        lab = np.empty(n, dtype=np.int64)
        lab[order] = np.cumsum(brk) - 1
        gid = lab
    k = int(gid.max()) + 1
    cnt = np.bincount(gid, minlength=k).astype(float)
    Vw = np.stack([np.bincount(gid, weights=V[:, a], minlength=k) / cnt for a in range(3)], axis=1)
    Tw = gid[T]
    ok = (Tw[:, 0] != Tw[:, 1]) & (Tw[:, 1] != Tw[:, 2]) & (Tw[:, 0] != Tw[:, 2])
    return Vw, Tw[ok]


def _join_chains(chains, gap):
    """Join open polylines whose ends meet within `gap` (cracks in the mesh)."""
    pool = [np.asarray(c, dtype=float) for c in chains]
    closed, rest = [], []
    if len(pool) > 400:
        return closed, pool
    while pool:
        cur = pool.pop()
        while True:
            if len(cur) >= 3 and np.linalg.norm(cur[0] - cur[-1]) <= gap:
                closed.append(cur)
                cur = None
                break
            joined = False
            for i, c in enumerate(pool):
                if np.linalg.norm(cur[-1] - c[0]) <= gap:
                    cur = np.concatenate((cur, c))
                elif np.linalg.norm(cur[-1] - c[-1]) <= gap:
                    cur = np.concatenate((cur, c[::-1]))
                elif np.linalg.norm(cur[0] - c[-1]) <= gap:
                    cur = np.concatenate((c, cur))
                elif np.linalg.norm(cur[0] - c[0]) <= gap:
                    cur = np.concatenate((c[::-1], cur))
                else:
                    continue
                pool.pop(i)
                joined = True
                break
            if not joined:
                break
        if cur is not None:
            rest.append(cur)
    return closed, rest


def mesh_plane_index(V, T, n, max_bins=4096):
    """Triangles of a mesh grouped into slabs along n, so that the triangles a plane n.x = d
    can touch are found without scanning the whole mesh. One index serves one normal.
    Returns (s, lo, step, starts, ids): s are the vertex heights along n.
    """
    s = V @ np.asarray(n, dtype=float)
    h = s[T]
    tmin, tmax = h.min(axis=1), h.max(axis=1)
    lo = float(tmin.min())
    span = float(tmax.max()) - lo
    bins = max(1, min(max_bins, len(T) // 8))
    while True:                                       # long triangles sit in many slabs
        step = max(span / bins, 1e-300)
        i0 = np.minimum(((tmin - lo) / step).astype(np.int64), bins - 1)
        i1 = np.minimum(((tmax - lo) / step).astype(np.int64), bins - 1)
        count = i1 - i0 + 1
        if bins == 1 or count.sum() <= 8 * len(T):
            break
        bins //= 2
    tri = np.repeat(np.arange(len(T), dtype=np.int32), count)
    first = np.cumsum(count) - count
    slab = np.arange(len(tri), dtype=np.int64) - np.repeat(first, count) + np.repeat(i0, count)
    ids = tri[np.argsort(slab, kind="stable")]
    starts = np.concatenate(((0,), np.cumsum(np.bincount(slab, minlength=bins))))
    return s, lo, step, starts, ids


def mesh_section_loops(V, T, n, d, gap=0.0, index=None):
    """Section of a welded mesh with the plane n.x = d.

    Every triangle the plane crosses gives one segment; its two cut points are keyed by the
    mesh edge they lie on, so the segments chain into loops without any distance search.
    Vertices exactly on the plane count as lying on the positive side.
    Returns (closed, open): lists of (m, 3) arrays (closed loops do not repeat the first point).
    index: mesh_plane_index() of this mesh and normal, for big meshes.
    """
    if len(T) == 0:
        return [], []
    if index is None:
        s = V @ np.asarray(n, dtype=float)
        cand = T
    else:
        s, lo, step, starts, ids = index
        k = int((d - lo) / step)
        if k < 0 or k >= len(starts) - 1:
            k = max(0, min(k, len(starts) - 2))
        cand = T[ids[starts[k]:starts[k + 1]]]
    pos = s[cand] >= d
    cnt = pos.sum(axis=1)
    cut = (cnt == 1) | (cnt == 2)
    if not cut.any():
        return [], []
    P, sp, one = cand[cut], pos[cut], cnt[cut] == 1
    lone = np.where(one, sp.argmax(axis=1), (~sp).argmax(axis=1))
    r = np.arange(len(P))
    ia, ib, ic = P[r, lone], P[r, (lone + 1) % 3], P[r, (lone + 2) % 3]
    sa = s[ia] - d

    def cross(io):
        f = (sa / (s[ia] - s[io]))[:, None]
        return V[ia] + f * (V[io] - V[ia])

    nv = len(V)

    def ekey(p, q):
        return np.minimum(p, q).astype(np.int64) * nv + np.maximum(p, q)

    keys = np.concatenate((ekey(ia, ib), ekey(ia, ic)))
    pts_all = np.concatenate((cross(ib), cross(ic)))
    uk, first, inv = np.unique(keys, return_index=True, return_inverse=True)
    inv = inv.reshape(-1)
    pts = pts_all[first]
    k = len(P)
    a, b = inv[:k], inv[k:]

    m = len(uk)
    src = np.concatenate((a, b))
    dst = np.concatenate((b, a))
    dst_s = dst[np.argsort(src, kind="stable")].tolist()
    deg = np.bincount(src, minlength=m)
    start = (np.cumsum(deg) - deg).tolist()
    deg_l = deg.tolist()
    seen = [False] * m

    def walk(s):
        chain = [s]
        seen[s] = True
        cur = s
        while True:
            nxt = -1
            for j in range(start[cur], start[cur] + deg_l[cur]):
                c = dst_s[j]
                if not seen[c]:
                    nxt = c
                    break
            if nxt < 0:
                return chain
            seen[nxt] = True
            chain.append(nxt)
            cur = nxt

    closed, opened = [], []
    for s in np.flatnonzero(deg == 1).tolist():       # open ends first
        if not seen[s]:
            opened.append(walk(s))
    for s in range(m):
        if not seen[s]:
            chain = walk(s)
            last = chain[-1]
            if len(chain) >= 3 and s in dst_s[start[last]:start[last] + deg_l[last]]:
                closed.append(chain)
            else:
                opened.append(chain)

    closed = [pts[c] for c in closed]
    opened = [pts[c] for c in opened]
    if opened:
        more, opened = _join_chains(opened, gap)
        closed += more
    return closed, opened


def _signed_area(P):
    x, y = P[:, 0], P[:, 1]
    return 0.5 * float(np.dot(x, np.roll(y, -1)) - np.dot(y, np.roll(x, -1)))


def _orient(P, ccw):
    return P if (_signed_area(P) > 0) == ccw else P[::-1]


def _point_in_loop(p, L):
    """Even-odd test of the 2D point p against the closed loop L."""
    x0, y0 = L[:, 0], L[:, 1]
    x1, y1 = np.roll(x0, -1), np.roll(y0, -1)
    c = (y0 > p[1]) != (y1 > p[1])
    if not c.any():
        return False
    xi = x0[c] + (p[1] - y0[c]) * (x1[c] - x0[c]) / (y1[c] - y0[c])
    return bool(int((xi > p[0]).sum()) & 1)


def loop_nesting(loops):
    """Nesting depth and immediate parent of every 2D loop (-1 = none).

    Even depth = outer boundary, odd depth = hole (islands inside holes are outer again).
    """
    n = len(loops)
    depth, parent = [0] * n, [-1] * n
    if n < 2:
        return depth, parent
    lo = np.array([L.min(axis=0) for L in loops])
    hi = np.array([L.max(axis=0) for L in loops])
    area = np.array([abs(_signed_area(L)) for L in loops])
    for i, L in enumerate(loops):
        p = 0.5 * (L[0] + L[1])
        near = np.flatnonzero((lo[:, 0] <= p[0]) & (hi[:, 0] >= p[0]) &
                              (lo[:, 1] <= p[1]) & (hi[:, 1] >= p[1]) & (area > area[i]))
        best = -1
        for j in near.tolist():
            if _point_in_loop(p, loops[j]):
                depth[i] += 1
                if best < 0 or area[j] < area[best]:
                    best = j
        parent[i] = best
    return depth, parent


def _crosses(M, Q, E0, E1):
    """True if the segment M-Q properly crosses any of the segments E0[i]-E1[i]."""
    r = Q - M
    d0 = r[0] * (E0[:, 1] - M[1]) - r[1] * (E0[:, 0] - M[0])
    d1 = r[0] * (E1[:, 1] - M[1]) - r[1] * (E1[:, 0] - M[0])
    e = E1 - E0
    d2 = e[:, 0] * (M[1] - E0[:, 1]) - e[:, 1] * (M[0] - E0[:, 0])
    d3 = e[:, 0] * (Q[1] - E0[:, 1]) - e[:, 1] * (Q[0] - E0[:, 0])
    return bool(np.any((d0 * d1 < 0) & (d2 * d3 < 0)))


def _bridge_holes(outer, holes):
    """One weakly simple polygon from a counter-clockwise outer loop and clockwise holes.

    Keyhole bridging: each hole (right-most first) is joined to the nearest polygon vertex
    its right-most point can see; the bridge is walked twice, so the area is unchanged.
    """
    poly = outer
    todo = sorted(holes, key=lambda h: -h[:, 0].max())
    for k, h in enumerate(todo):
        mi = int(np.argmax(h[:, 0]))
        M = h[mi]
        segs = [poly, h] + todo[k + 1:]
        E0 = np.concatenate(segs)
        E1 = np.concatenate([np.roll(p, -1, axis=0) for p in segs])
        order = np.argsort(((poly - M) ** 2).sum(axis=1))
        qi = int(order[0])
        for cand in order[:64].tolist():
            if not _crosses(M, poly[cand], E0, E1):
                qi = cand
                break
        poly = np.concatenate((poly[:qi + 1], h[mi:], h[:mi + 1], poly[qi:]))
    return poly


def fill_polygons(loops):
    """Fillable polygons (outer boundary with its holes bridged in) from 2D closed loops."""
    if not loops:
        return []
    depth, parent = loop_nesting(loops)
    holes_of = {}
    for i, dp in enumerate(depth):
        if dp & 1:
            holes_of.setdefault(parent[i], []).append(i)
    out = []
    for i, L in enumerate(loops):
        if depth[i] & 1:
            continue
        outer = _orient(L, True)
        hs = [_orient(loops[h], False) for h in holes_of.get(i, [])]
        if len(hs) > MESH_MAX_HOLES:
            continue                                  # too many holes to bridge quickly
        out.append(_bridge_holes(outer, hs) if hs else outer)
    return out


def fill_trapezoids(loops):
    """Even-odd fill of 2D closed loops as convex quads, (m, 4, 2).

    Horizontal slabs between consecutive vertex heights; inside a slab the edges cut it into
    trapezoids (pairs of neighbouring edges). Convex pieces need no polygon tessellator, so
    sections with many holes cannot tear.
    """
    P = [np.asarray(L, dtype=float) for L in loops if len(L) >= 3]
    if not P:
        return np.zeros((0, 4, 2))
    A = np.concatenate(P)
    B = np.concatenate([np.roll(L, -1, axis=0) for L in P])
    flip = A[:, 1] > B[:, 1]
    lo = np.where(flip[:, None], B, A)
    hi = np.where(flip[:, None], A, B)
    keep = hi[:, 1] > lo[:, 1]
    lo, hi = lo[keep], hi[keep]
    if not len(lo):
        return np.zeros((0, 4, 2))
    x0, y0, x1, y1 = lo[:, 0], lo[:, 1], hi[:, 0], hi[:, 1]
    slope = (x1 - x0) / (y1 - y0)
    ys = np.unique(np.concatenate((y0, y1)))
    a, b = ys[:-1], ys[1:]
    # every edge spans a run of slabs (its ends are slab borders)
    i0 = np.searchsorted(ys, y0)
    count = np.searchsorted(ys, y1) - i0
    ei = np.repeat(np.arange(len(x0)), count)
    si = np.arange(len(ei)) - np.repeat(np.cumsum(count) - count, count) + np.repeat(i0, count)
    xa = x0[ei] + (a[si] - y0[ei]) * slope[ei]
    xb = x0[ei] + (b[si] - y0[ei]) * slope[ei]
    o = np.lexsort((xa + xb, si))                           # left to right inside every slab
    si, xa, xb = si[o], xa[o], xb[o]
    cnt = np.bincount(si, minlength=len(a))
    rank = np.arange(len(si)) - (np.cumsum(cnt) - cnt)[si]
    li = np.flatnonzero((rank % 2 == 0) & (rank + 1 < cnt[si]))
    ri = li + 1
    q = np.empty((len(li), 4, 2))
    q[:, 0, 0], q[:, 1, 0], q[:, 2, 0], q[:, 3, 0] = xa[li], xa[ri], xb[ri], xb[li]
    q[:, 0, 1] = q[:, 1, 1] = a[si[li]]
    q[:, 2, 1] = q[:, 3, 1] = b[si[li]]
    return q


def hatch_segments(loops, angle_deg, spacing, max_lines=1500):
    """Scanline hatch of closed 2D loops with the even-odd rule: (k, 2, 2) segments.

    Lines are n.q = j * spacing, anchored at the origin (so the pattern does not move
    when the plane or the object does). Holes need no special handling.
    """
    empty = np.zeros((0, 2, 2))
    loops = [L for L in loops if len(L) >= 3]
    if not loops or spacing <= 0:
        return empty
    a = math.radians(angle_deg)
    nv = np.array((math.cos(a), math.sin(a)))
    wv = np.array((-math.sin(a), math.cos(a)))
    P0 = np.concatenate(loops)
    P1 = np.concatenate([np.roll(L, -1, axis=0) for L in loops])
    sl = [L @ nv for L in loops]
    s0 = np.concatenate(sl)
    s1 = np.concatenate([np.roll(s, -1) for s in sl])
    lo, hi = np.minimum(s0, s1), np.maximum(s0, s1)
    span = float(hi.max() - lo.min())
    if span / spacing > max_lines:
        spacing = span / max_lines
    j0 = np.ceil(lo / spacing).astype(np.int64)
    j1 = np.ceil(hi / spacing).astype(np.int64) - 1      # a segment covers [lo, hi)
    cnt = np.maximum(j1 - j0 + 1, 0)
    total = int(cnt.sum())
    if total == 0:
        return empty
    seg = np.repeat(np.arange(len(P0)), cnt)
    first = np.cumsum(cnt) - cnt
    j = j0[seg] + (np.arange(total) - first[seg])
    s = j * spacing
    t = (s - s0[seg]) / (s1[seg] - s0[seg])
    q = P0[seg] + t[:, None] * (P1[seg] - P0[seg])
    x = q @ wv
    order = np.lexsort((x, j))
    js, xs = j[order], x[order]
    new = np.ones(total, dtype=bool)
    new[1:] = js[1:] != js[:-1]
    gstart = np.flatnonzero(new)
    gid = np.cumsum(new) - 1
    gcnt = np.diff(np.concatenate((gstart, [total])))
    rank = np.arange(total) - gstart[gid]
    i0 = np.flatnonzero((rank % 2 == 0) & (rank + 1 < gcnt[gid]))
    xa, xb, sj = xs[i0], xs[i0 + 1], js[i0] * spacing
    keep = xb - xa > 1e-12
    xa, xb, sj = xa[keep], xb[keep], sj[keep]
    A = sj[:, None] * nv + xa[:, None] * wv
    B = sj[:, None] * nv + xb[:, None] * wv
    return np.stack((A, B), axis=1)
# END MESH CORE

VERSION = "0.8.1"

# Project icon (96 px PNG), shown in the panel header and as the dock icon. docs/icon.png is
# the 256 px source, docs/logo.png the full logo with the title.
_LOGO_PNG_B64 = (
    "iVBORw0KGgoAAAANSUhEUgAAAGAAAABgCAYAAADimHc4AAABJ2lDQ1BJQ0MgUHJvZmlsZQAAeJxjYGB8wAAELA4MDLl5JUVB"
    "7k4KEZFRCgxIIDG5uIABL/h2jYERRF/WDSxh48avFgNwFQEtBNJ/gFgkHcxmFACxkyBsFRC7vKSgBMi2ALGTC4pAbB8gWyk5"
    "IzEFyAa5T6coJMgZyJ4DZCukI7GTkNgpqcXJQPYeIFsF4c/8+QwMFl8YGJgnIsSSpjEwbG9nYJC4gxBTWcjAwN/KwLDtMkLs"
    "sz/Y74xih3JzSpOhfgKJ8KTmhQYDaTYglmHwY9BncGRgKE4zNoKo4HFgYGC9+///Zy0GBvZJDAx/+////73o//+/i4HuuMXA"
    "cKC9ILEoEayWGYiZ0tIYGD4tZ2DgjWRgEL4ADLZoHPZxgO0rZghicGdwAgB7LE511UgBAwAAHKVJREFUeNrtnWmMHOeZmJ+6"
    "uquv6p7unuHcMxxeM7xJixTXsiRfMhRE60RI4gOGvZtdZL1Bsr+S7C6SINkgWCAwdvMnf7zxGlgYaxhe2FB2JQhcU7JsiTos"
    "UrzJ4SEOh3MfPX2fVV1V+VHVNT2cGc4MOZQokS/Q6J6a6uqu9/ne8/uqS/jhXJm7iACIgOn+rQHPAV8BDgG73G22u++jJI1z"
    "zgPXgLPAL4AT7jYACbDcfVdW8F0AiO6bAfYA3wG+BvTzWO4mo8DfAT8CLq+gy3UBkIG6O7r/2H0oTeQtl77wCI78lSyh8RCb"
    "9GEA33Mf+SadLgXwk7nqndsk1+UcAn7oPuO+WXqs8HUBMV2F47qm33efpSZ37pnGSsr/GvC6q3yjySoeK39tEZqUb7g6fN3V"
    "qenqeImrudPt/Avgp+42s8n1PJaNi+LqsMXVqQn8vNkdiU2WUAf2AT9wd1xG67Hck0hN+vyBq+N6Q/diUyDVgB+7tFhJ+d1z"
    "r5FcOIOvln6s1o1DwNXtj11dC4AgNhH60yY6y5Tvq6WpSnHy4X7yCyceg7g3CA0v86cNDyP8ZK4quAXVBdcixJWCra+WRiuO"
    "kkoc9v7OL5xwqrPEc+j++GMVry9DstzHfuCa6G78PTdgrFrRBu8o5nR/HLXz62iJ59CKo1Snfkqs8Ngi1pEh2a6ufw+wRdcf"
    "fXM1v7+W6P44qcRh2hNfRtYfg9hAPPgmoMnAl4Bu1yzEez1q1p8AfwKt1o9cHKV77gzFwGGykceuaQUrsFydf0kEXmjyT/ct"
    "QR3qvn6KgcPI+ijdc689toiVYwHAC7IbDNhIlRuzRbKC5b2mmIJw0nkG8q+O0VIMUO4KU3+q3wXhWATh5JL3Nl4/glYAsF+O"
    "2eLOtQA0lBRsKpxjtuutiinG/++bbNmzG99TSfS3HQiZcAWVIPx0gnJ3mDJhkkcmsObPIEtx6vEnyArW4nEeTQA7ZTcI3xXA"
    "qkoqptDfTpF5ewzpdg3zpExvbAeBlgCZcIVqrkw1AiqgXy2QIgL04nsqSfyNn6Md2EY+fvBRBqDJbHAy5U4Y+YRAN52IKYn8"
    "eI4zgTfYkmynq3cIscXvgaDDCf7F4XF8VwsI9W20cJM4N6k/uiDs9Xc49dV3K9pFNKJogSgaUfLjOSYZhjGWgZA7E/iiQbhU"
    "JXNmG6LlI8rwowpCkDfjKGEhvORvLRCFFOQrOW5lzuFr8dPVO4QdA71bdSxib5BgAeq55SDoiZPu3Qu+1k89gU0B0LCAO6U9"
    "0EHZLJMfz3F+4lcku7fABeg5cBCKNnW7BoDY4se0ax6IOf0MO8bTjwSIdQOIGXk2mjCWKXsW0XBNWSGPnvmNZxVWpcb4/LDn"
    "qky7RvLSXnKWD3NEJz7w5qcaxANxQauJB6KYI1WapWbq9LcPsr1nP6VKkcmxpSCELGTObCOlX/IsIty5m7HglkcTgChoS/6O"
    "tLWTurqwqgu6Gwg5GaA+XuHi9LtooRh9O4c8ELViEX84jNjiB1hiEQycJP4pArEpFhAkwQoT/nd/T8oHAR8aUaySycWzDojO"
    "bduJhVqoYFAZX1gCQshA7vQQ1hkdDp8kEbUIDT7ziQZxzwAiQXnTvoSoSvTSg1UyuXrh9JogaIAQdezcSeJA+MnPfSJByNF1"
    "NEBzK4TfhZcukU8ICAunKKFvyAWtB8TM+eukegIAbO/ZvyYIcCzC3PoZ7Jbt5LCI8vC3OYR3Zuv2egDEMiMAmF07KczNcOF3"
    "/pZCT52tdpfjTh6Q5Cs5rLDoZU3AshhhZWqIlg9L1Gk5fBMhamH070CIH37oQazLj6x0AsnuLXSPSxTtIgQeHAAtEAUT8uOL"
    "Rd16LKLl8E3gJtqBbRA//OkMwqIqbYrr2SiID7mwzDUpkoLQ4QdB8EA4g2cY3DaH8BCCkPmESXOb40rmlGcRANmJDIpU80CY"
    "dm3RIrj5UILYMACx7ATkmqmjViVEVfr4QLgWcSeI0nSRiunECbVXpjyhL7OI8JOfc+JbsOPhD8IA0ewN5wvHdjjPxTnyr46R"
    "fuUCWin4sYFYLVgHbIVStYhhGvjDYYLdQUrFMkIWRMuH2ivjb7tI+MnPLYOQK84xUzhBe+LLRH1bHk4AAFZQpDA3w9R/OYGe"
    "qX2sIMpJnWDKtwRER+sAITW8Iggp7WRNqb2XaBXm6dl2EKH/S4xKFhdG/4J54zKtyh7a/F0PFMR9AQCwJyfJnZynUEyTG53H"
    "vF1CLFqOi/iYLSIr5El2b1liEQBiwE+wO8hw6C+5WBMJRBW2V2v0+waZt1u51XEVnxajzd/FdHUYSdAw7TySoLE/+btEw20P"
    "D4D5f7yCb6KKHRZRJB+GqZOZniV/ZvKhAREkgd5TJhnvwdcdRsjC5NgwHxw6jpSQUAOLzcQZ6S0+VzrqFJt7ttChDnG5+Atm"
    "zOu03NiFf9BmT/grtEeeIxpuo8WEjPQxAIiWpwG4/fKst48i+QigYJkmRapMXLr2UFhEkCAzlWnGe9M8te/LRKIRjp98iVTo"
    "CsoxkAxQtDBpcQxduI1la4hC3gNxyTYw9qSWdoDNBK3KHs8i7hXEPaehpZLE9JnUihcPiJKEgo/uvbso7KuTmxgley7/sYFo"
    "zEuEYxr5iIUeMfjwwK8YF86w773nMXeYQBG9ZVH5ACdD73vHOHQFpnYdpCgtAFCUFihabzLxxhUOP/HcEouA9cOQW8y1d2o+"
    "WLQ8zZgl8faf/w1b7S7CT+0iLga9/1cwCKBgmLrTtLNlIl3bKXQ7IDIjBaLTgY8tWEdsGWGiCiIIfUXOx15BzMqE8wk0K4kv"
    "bmHZTttdFPLYHUGE6TJnQ8DEOQ6V4GwIb7sVynG56DiRmQJ0+3cQih9lPXqFdS5FXOlgPWNx6uMVbv79r/ng0psYpk4AhQAK"
    "ebO04olv7d1N4pl9lJ6SybQUsarmxwJB71a916GIRKDHJh+bZap4jdRYGj3tqMWyNYTppRcxntnuDLbGdlHIU7sqMF0dBuBU"
    "7h94a/R7FNJzm++CLCGJSNUrhIIEnRmuCznO3Xid5EA3Pf07UKLOCTasoCGGqRNBJt67G3phbmKczIdTSFMmYSH8wK1i1HiP"
    "7liQtsnPLFsLEopIELHJF2YpZhcIFxNo4SRqgiUWIUyXvdHfkGz4LIadIl0cJ5hpBxZY2A2RBxUDtJzBqFTwrvdrD3Q4IC7n"
    "uHDlV9j7gmzt2Uk82r4iCIAACn3dA1S6e0jnZlg4exshb29KLREkSCqZXdKlbUybni79kh5fAcMsoawQwRogTFJMjTsgwoKI"
    "GAJfXEPoXD7xFCsewiBFZjzDrJEiLK8/zkn//j/8tz9bz462nsYWgghSnUw6R/bVMfyKO9LdCynNDpGkHkecNJicGMVMFTFj"
    "AuFAFEmUsGyHWFhcdAEKEpoaRevvgHaZTDFFzajhq8gI8sbbyLcY44P+N+jSt2EETe9RzZX5sO0mUptApjbBLDdBq931WEoU"
    "ykKG1ktPkOzoxKeqbFUPYY34GTJmmPE51iHvtFAuJykJTp0RrGpUIpNkaqPUxXZiSmgTLMAXBgNEfwddAx3oX68x/c5lfONB"
    "5IAzKhojrnkVxOjEOYrdWwjv7yAebSewykWXARS6oj10fb6Hydy4W9QVNmQRQYL0t03x8pFX2Cmf5Q8z497/fsL/IWwrCKXF"
    "uGOKOpK1Ris95wyWlnCfM+uaEejo2ENoRqHd9JMWx1AuxymH0t4FvR17u70ibro6zIw6xLG2b917EF5J+n57C5/9399CfCa4"
    "ajDVAlEG1V3UxyuMvnqOsbfOMpkbX/PYXdEedh84TP+zByntFshKhXUF7HxF583gAtujXUuU/+pkN75xJ3j6NIlALEpb38a8"
    "r1Ep4FOXrw70LcTI+uYX3ZHeSoc6xFxtEhaimGMhpien7i8LWvGN/g6s2jRyZ8KZlLlLDt4AoU5IjL56jmtvvb8uEJFoZF0g"
    "ykmdekVG7ynzn9ve4a8mxvl+S4/3/78cnOL7X/23jEWvUf0AFDc8rjn6ASu23OdPT1+mxPtUK0UKvgXsKujG0u9lpgTMUp1q"
    "vcDh8HNYtekHNB9QyK9rXVCZMqIqkUxucUBMnKPYPU14fwdd0Z51gSj0F5i6MIyeKRMutqD3OJlIQDzD5559mWQ8RSqd5Lvd"
    "PXyYm+TVTsfdhZw8mErfVS7evkX0+lbMtjr0rGOgZZerSAt2EqoolEOzCAb4FAndMLGrkGGeK5ffRVO6ABiqD9K34+DmZEGi"
    "Ur3/tkDKByrO5PuE6YFQtybp6x5YE8Sup49SwWDsrbOO4vsdxQ8Pv8iJkS9yKnyCW/yMUGR54JMsn5Pz911EtUIbq/ylaULu"
    "Sn5VjgDz9HGQgpQmzRg+RQLFsYTp0i3SkTF8dpgjff8EqzaN6O/YhDrAUBH9K2y3/YgbXBcETasgJkwmJi5T7Xb6LbuePrry"
    "55smoiShJS7zzSf+CIAp8Tv8zbsHiEzF8AHP9CW4tMbnblT5ywq5qlP5ClKAFq2PSD5OwUqTFhdB1AomQdHHdPQy07nLHI1+"
    "cUUI9zcn7O8AhhGFGvfzqwZLQDDF7Ev/wJZkuwdiIWKQKCj42y6yb+K7MOEofkr+QzIxi62HqkxJwwRTPn4dXPjIKmrbrGCW"
    "AghSAE3qImIugvBHJLoHdjNXm0TPZ5mYv0x3655l2dBDNSfcAAHOVOPxky/R2zvAgUM2+yqLip/x/zsXikSiIEFUYdfTR8mb"
    "JQ5PvsD82C1mez9AQVlXoN2oBBIKzDgWsKS1fAcIPZ9F0lugFKFaL6BMm/DlTbKAeqWMHAhSLxibfoL1iowWiPJi8F1apb+G"
    "C/D/Rv81sWPfJoyKCLRkxWVGp0khdvceYND8K8b093lp5ofMaOcJaP7N6SG5roeqc85z+WtowU43JixaRQMEGTCbXHOyb/9y"
    "F1SvlNfuVwSCy5S/2QqXA3XveffgKwwNvQTA8PCLXL/9PGZF5tzc62xJttO5f4hINLIkLtzZDu/NHuWYkOWDbIhM7jZ6NAOx"
    "yn1ZhCUX8QsyhrFYyd8unicSjhK242hKF4IUwDYrS6yiWi+wffce+toOLtPd2hZg1oAgwvQVxEQv9Yp/04JwI4c/GDrOudIX"
    "ORg6vkzxDShyoM5WesmP5zibegNxR4gDPUc9EIVcwcuUGhAWtGmSZg+tPmcK8frtU+Rjs6hRc8MgjPcgf2wKLdjpFU97BYWx"
    "8AHSjDJj3iItjhG3er0U1DYrVOsFhuqDHIi8uOLAlR0Fr+1upGVQnOK/eiuFKkj3FITLSZ3nBv4HyXiKIV4ilU56ii8ndYLg"
    "tTmaq+tGB/bsDeeCwOZaopArEAoHmS5OkdMm8UsiGCCJYXYmjmAumMzmxkhrNzZkEcoxJ/9vVMXIMBvsQJUCdLKPKgXS9lIQ"
    "ETHO011fo6t7J6vpeV0xQBRzS15bpkpFN7x2671awMHQL0nGF6f6Toz8d6+3tNZ6U68D6/WbFos6yzQ5mzjhKd60iphWkbph"
    "EYxFOaA9Sy6/j9Gxi2uC8EVFRlpPcnDhGfwhR121SB0qiz6/ZtfxCzKd0iKIKfE8mu0MikqlSCAQBrNGRTcI+Bb7YcL7l6bW"
    "nBMOhUyE6SvYiV5KxtJWq6EbTBy/xsLZ2xue6bLb3mNXIOv9ff328/fsn5tXQZwKn0A4aBFUNMpGHqFkY4cEgoqG5ipRkJyi"
    "KpdPM5pbG0QlXyN6Y4jfevKrVOsF2gpX+FCKoQbCRMQ4NdsZgH73useaXUe38wS0EKqYpKOrkz3yc/dmAaWSRBjI28IyR6P4"
    "FPZ+c4jSV/dy/cxxMi+bRKcDXlp5NxHmjnGl4nwFvadM8D4CuRaIEqwkeDv895w/8got13fQm9tF6IgGMahkcxBrzuGdeV8t"
    "JK/LInyxxUac2gpqpZWMOQWleXzhxSuHGiAAfIKGXJQp2RmuZG+jmCYHjv02Fd3Y3DqgVHIUvfPw81QHS4xdfYv8OkE0fLy8"
    "CUvcnYLQTRk/M8LFcafv05vbhXJMQlPlVQqqPFpIpp99bMn2MptfOUYkjpSp1gvgNj8j4SipzCRpRomv8nu2zUDuuxsaTd++"
    "e6agG6jBEDsPP8+h//k09h/o5Doqzmq1j2D+17KdDE2KOj2rQI9N5chVLu44zuWR08xOLiBImud+mqUo1DGtIlJCoj+6j6Hc"
    "lwicGsTMS5iiM6O3cCqIWbAxC47X1t0JmMbzqvWDneeAeZTewaeXjH4A2dDXLqQUn0JGHaSlehX70q+J9MbJqIMobjCplktI"
    "ss+DYNZ11KDGzsPPYx7NM/e+TurVs9THix/J3O9KDTizb5Lzt1OMnt5Kf9t22nu3em6oKNQx8otKNK0idkhg29AuYBf1lMVV"
    "+TWq/sKyuQCEHLWCCas0hFU5wiH1K/QO7Pb0swSAWdfXLgXcfYraPmoDJTBGkK+/g90Tp6YMoAZDnuIbUi07KyMkOUDHYY22"
    "o09y68KHFF/LYV/OPRAQzS5oNRCVvqucv32LqxeTDEYPcSCpMuMPkWnsZ0DNtBBKNnUsWvs6UFSJ+PzvkuteQIoIngXIqojf"
    "CnujvOH3G3IovKj4hj7uqxnXOEg9MIg5oOM3RvCPnMbuiWMqA0iyjzuBmnXd3SaxffdhzP2ORcyevLjpIBouaCMWcfVmkp1z"
    "TyActAi3aBj5IkLJUXC4RUNRJYyqidoqobYmMKruz6lWIGPNUzOK+JWwp/gGiIgYp6N7x6qKv68g3FDynSAAzIEnVgSxCFCi"
    "43CStqOfeWCuaSvbmGZm3SAuZieQbrfRWdxOXEggJSQkAwJayFV4kztWJRQVqiPz1OqO22oRW5dkPrqdp2ClmZ64QVt73+YF"
    "4dVAFOxOCt17oSeOf+Q08vV3nOwoEULXl0/i5LMLGHmJlsEAu//sSdq/+9kNzf2ulVHd4iYdYvv6Y4Tmx7cvx3jsHS5lf4Px"
    "nlPAKSsMCCkiur69Fcsd3PXq0qtIfYKGT9D4TeFnnJz/GeVKbvVU/LWTF+3NDnwdXTFKV990irjBZ5iezN51f59PRder5LML"
    "pN6awTyXv+f1QVbV5K3B44xFr5HbMcxArI9pa2ZDx6jka4RzXexMHHG6na2O4s2Co+j8XJ6O6lu8W41hlaAjPEhYijdBEpZk"
    "QJrSxbP931hxMD4QAN4U4sQlhKj1kYMIEqRYLSwB4YsJG27AVfI1xzVFt9PTM0DLNqeSGz89RjF5nvJYjEAsTLe9HwMnQ1KI"
    "eK8BaqbBsfBT9A4+/dEDaAYBIEQtqjcOoB9e30duFogb4lXeP/KP5HYMI8TqG56SrORr2GNRDnQ+S7hFYzR7ETWRpTwW80Z/"
    "s9K9VRcRgaH6IMm+/cjSygmCcPzXpx84gMaHV8pFtpgj2DnHjxa69zo+9I5OoVFzcuVAMLxpIBrXB6QPXmQ4+jqStrFYUxVL"
    "aKf2Ed8Vp2YUURNZ7Hw3feED6HYeyy0jYi1dHIwtTns1zqG+SjdUePkX7z5wAJ5/ngkRGhCYGTnFzlY/dk7khl4hwhNORtC+"
    "csqm+BVkyU8+u0A5PULhx/UNgSgndVITs9j7gvTEtlK9leJvP/+fNgxBvxilM7odQyzxVCLLtPr0sn2ejPxLYvEtVMrF9dUu"
    "fIQitpeolItE24eYnt/HXLyfHb4A7b7LFDjtQVrW4qgZVMpFFJ+fZN9+tvzRTuw/0Ne9xL3R2m7NRChZBeZbCvd8DoboFpj1"
    "rStbSnZs3cr/yAHcCQNgLt7PXLyfna1+2tKjHohVFVAzPBDtv7NjQyDuRfGVcQFpPElVLFF3K+22YJ+ThhbxHg05L71Pbmb4"
    "4Qdwp8xKA9zQK+zwBWhLj655Es0g2r69dQmIO2EE72h0t2Yi63ebsTp7Y1+ge/QZerU99Ef3LclwvP2aQIwoH64/PvIQSbR9"
    "iEm9huLzw8wwbelRbugVou1DGI3tK4DwqyH87UOo3y5RzY6Rf9lcctFH4xqxe7LUrAwx6OkZ8BQcVDSq9QlMS6NsOVNjkugu"
    "UcmBJaWphUr41bWzLdnQaw8TA8rpEYLxAYLxAW6knZ/IaYAACMYHluznjUCrvgREanaK3C8qSFOm84tegjPyTW0Dlb6o4891"
    "eRM5YnhxtDcr/Vj4KQDeK76NaVWIJfvxqyHWo1vZsuoPFQA11kvjO6mxXkRRZtyqgz7GDl+AG+kR1Fivp/zm71+rLmZRXX07"
    "qLkgKqd0MhcyFIQ6vQxsqJVd6lteRYthwIVwLPyUZ6GfVduoVEpE1QSGXmM9un3ofy2lcRLB+IAHoqc8zw294gFa6UQL2QV8"
    "qkpbRy/WC3WsIyZaNE4kluDWjYvr/nxlNO7dvNFaJblpKNunqqjBMJZVZ70DW9arVT5JosZ6uVmtAhUiuQ+Yt1sR1TbUYJjq"
    "Helf87klt3SiV6vUqiVC4ai3qmEtqQs1JjMjtBhJgspy/zUsX2VP+d5/uqBxD5lPjDSUKqptLPj3AJCoXaacHqGuV9d8H0Cp"
    "mEPfQGA2xBLF5HkmMyOUjfzSvL+Qv5/TsVe8Y9InSRogLFFji32TRO3ymiBC4SjhXBeVfG3NIKwScfo9qQMYYolMMYVpFVHl"
    "TfkVX0Fk8d639icZhOxTWfDvYVbYtiaIQCDEtzv+hH2n/7k3b9CYeL+bvNj++7zQ+Q0kNx0yrco9j/xGv1EGrgNP8Am/KXND"
    "2bJPZYE91PUqW+ybUINZYRuyT/X2k30qNTtE7EgHShGM1BwZYfkCXsnyoduLYG6pk2zjEAfELxPInSaqmOwNDC057gYACMB1"
    "ua5XLzQB+MRLA4Ro5Zmn1XNN89VWL+hZ1TyKpLG/5Vms6hyl1re4WOshlR33VlJLmokp6sjC4hzC1mqXczsQQNNa2O93QFvu"
    "Z97N9a1iARdkwzRfwbmp2KfqVrWKu/bHME3mBQeEaC0GTMM0MSolFEkj4P+nHFPylPxLQZh9U9TtlV3TvN1KrVJCkSQMc8PT"
    "qA1dvyL9sxf/1RTwbSDKp+je8JZtY9nOQDPxYdk2smBgiRqCXaNW/yUBqQPdkrFsG1EKoMg7CVUTHEjupyIIiLMadkFAizkw"
    "w3ovgigiiSKCXfOOew/+XwQmgP/YCMI/aQR+PqVi6DWKNRnDNKnZIWzrCyiVOer144SrtyhXyhimSSgcxRI1dtpP8kLnNxjY"
    "th+hZBNUNHyuj2+2pHuQho5/AuSF7//gR+u6meenWVqsKbLyNWL1XWTEzqVpq14lHpFJF+oegMa2Yk2+l9G/7GaeEnAV+AtW"
    "uOf5oyAZsRPb+oKbmL9Bi7X40wI+n0qxJnvKb4i/cP1eR7/k6voqIIlNG/8XcNHtDz1SEBqrFVYC0bySYaVVDfr6Mx/T1e1F"
    "V9cSYMq6c+mf7caCbwG/xrm52yN1S/NmRWZ8nejVOMhp/Oq7xOq7mK3Hl1nBBiA0BnTG1XG+0QZqzIhZTXT+jav4R9Id3WkR"
    "tepvYQTa6GCEhH5lIyP+TrcjubpteBmrUZd4NYy708+Br7u0JLxfwXl0Qcymy0wzQC2ykw5G8KvvOk290prZkOHqMOPq9Ocs"
    "3tqcOwE00/o7nPsMnwXvF5bqn5ZqecNFneLzQIwZ3YSUp6lFdt4t02koWHF1+CVXp8u8imwY+mrB4izweeCP3YdyRyolND0e"
    "KZlNL7ayDUNvxFC7KYWX3dH/PfeRd7ctm6WRWbmMrrsHywP/1S0avgN8DWd+SOKxNLcVmgfhqDvafwRcbvI0K06RyZa1apxt"
    "jHLRPdCfAH8OPAd8BTjkFnDap6mFscGiSnAH6TXXY/wCOMFii19qKrxWlP8PFJ7OB0Gn7r4AAAAASUVORK5CYII="
)


def _logo_pixmap(size=None):
    """The embedded logo as a QPixmap (optionally scaled to size x size), or None."""
    try:
        import base64
        pm = QPixmap()
        if not pm.loadFromData(base64.b64decode(_LOGO_PNG_B64)):
            return None
        if size:
            pm = pm.scaled(size, size, Qt.KeepAspectRatio, Qt.SmoothTransformation)
        return pm
    except Exception:
        return None



# ----------------------------------------------------------------------
# Toolbar button: registers the macro as a command on a global toolbar
# (shown in every workbench), the same as Tools -> Customize -> Macros.
# ----------------------------------------------------------------------
TOOLBAR_NAME = "Live Section"
TOOLBAR_SHORTCUT = "Shift+S"      # only assigned when no other command uses it
_TOOLBAR_PARAM = "User parameter:BaseApp/Workbench/Global/Toolbar"
_MACRO_FILE = globals().get("__file__")


def _macro_path():
    """Absolute path of this macro file, or None if it cannot be found."""
    import os
    if _MACRO_FILE and os.path.isfile(_MACRO_FILE):
        return os.path.abspath(_MACRO_FILE)
    guess = os.path.join(App.getUserMacroDir(True), "LiveSectionAnalyzer.FCMacro")
    return guess if os.path.isfile(guess) else None


def _macro_script_name(path):
    """Commands refer to macros in the user macro folder by file name only."""
    import os
    if os.path.normpath(os.path.dirname(path)) == os.path.normpath(App.getUserMacroDir(True)):
        return os.path.basename(path)
    return path


def _toolbar_group():
    root = App.ParamGet(_TOOLBAR_PARAM)
    for g in root.GetGroups():
        if App.ParamGet(f"{_TOOLBAR_PARAM}/{g}").GetString("Name") == TOOLBAR_NAME:
            return g
    return None


def toolbar_installed():
    return _toolbar_group() is not None


def _reload_toolbars():
    try:
        Gui.activeWorkbench().reloadActive()
    except Exception:
        pass


def install_toolbar():
    """Create the command and the toolbar. Returns (command name, shortcut or "")."""
    import base64
    import os
    path = _macro_path()
    if path is None:
        raise RuntimeError("the macro file was not found; run it from Macro -> Macros...")
    script = _macro_script_name(path)
    icon = os.path.join(os.path.dirname(path), "LiveSectionAnalyzer.png")
    if not os.path.isfile(icon):
        with open(icon, "wb") as fh:
            fh.write(base64.b64decode(_LOGO_PNG_B64))
    shortcut = "" if Gui.Command.listByShortcut(TOOLBAR_SHORTCUT) else TOOLBAR_SHORTCUT
    cmd = Gui.Command.findCustomCommand(script)
    if cmd is None:
        cmd = Gui.Command.createCustomCommand(
            script, "Live Section Analyzer",
            "Interactive section view (Live Section Analyzer)",
            "Opens the Live Section Analyzer panel",
            "Interactive section view", icon, shortcut)
    else:
        shortcut = Gui.Command.get(cmd).getShortcut()
    if _toolbar_group() is None:
        root = App.ParamGet(_TOOLBAR_PARAM)
        n = 1
        while f"Custom_{n}" in root.GetGroups():
            n += 1
        grp = App.ParamGet(f"{_TOOLBAR_PARAM}/Custom_{n}")
        grp.SetString("Name", TOOLBAR_NAME)
        grp.SetBool("Active", True)
        grp.SetString(cmd, "FreeCAD")
    _reload_toolbars()
    return cmd, shortcut


def uninstall_toolbar():
    """Remove the toolbar and the command created by install_toolbar()."""
    g = _toolbar_group()
    if g is not None:
        App.ParamGet(_TOOLBAR_PARAM).RemGroup(g)
    path = _macro_path()
    if path is not None:
        cmd = Gui.Command.findCustomCommand(_macro_script_name(path))
        if cmd is not None:
            Gui.Command.removeCustomCommand(cmd)
    _reload_toolbars()


class _GizmoEventFilter(QObject):
    """Qt event filter: forwards mouse events of the 3D view to the gizmo."""

    def __init__(self, gizmo):
        super().__init__()
        self.gizmo = gizmo

    def eventFilter(self, obj, ev):
        try:
            return bool(self.gizmo.handle_qt_event(ev))
        except Exception as e:
            App.Console.PrintError(f"Gizmo error: {e}\n")
            return False


class PlaneGizmo:
    """Double-headed arrow + plane outline, draggable along the plane normal.

    Dragging is implemented with a Qt event filter on the 3D viewport. It sees
    mouse events before FreeCAD's navigation/selection code, so a drag on the
    arrow neither rotates the view nor changes the selection.
    """
    PICK_PIXELS = 22
    COLOR = (1.0, 0.55, 0.0)
    COLOR_HOT = (1.0, 0.9, 0.2)

    RING_RES = 12                             # segments of the short arc
    ARC_HALF_DEG = 22.0                       # arc = handle +- this
    HANDLE_DEG = (55.0, 35.0)                 # handle position on each ring (off the arrow)
    RING_COLORS = ((0.95, 0.15, 0.15), (0.2, 0.4, 1.0))
    RING_HOT = ((1.0, 0.6, 0.6), (0.6, 0.75, 1.0))

    def __init__(self, view, size, on_start, on_drag, on_end,
                 on_rot_start=None, on_rot_drag=None, on_rot_end=None):
        self.on_rot_start, self.on_rot_drag, self.on_rot_end = on_rot_start, on_rot_drag, on_rot_end
        self.rot_active = None                    # 0 / 1 while a ring is being dragged
        self._rot = None
        self.fixed_axis = App.Vector(0, 0, 1)
        self.view = view
        self.viewer = view.getViewer()
        self.widget = view.graphicsView().viewport()
        self.size = size
        self.on_start = on_start
        self.on_drag = on_drag
        self.on_end = on_end

        self.origin = App.Vector(0, 0, 0)
        self.normal = App.Vector(0, 1, 0)
        self.u_axis = App.Vector(1, 0, 0)
        self.w_axis = App.Vector(0, 0, 1)
        self.half_u = size
        self.half_w = size
        self.dragging = False
        self.hot = False
        self._anchor = None
        self._grab_t = 0.0
        self._removed = False

        self._build_scene()
        self.sg = self._render_group(view.getSceneGraph())
        # first child: the scene-wide clip plane (added later) comes after it,
        # so the gizmo itself is never clipped
        self.sg.insertChild(self.root, 0)

        self._filter = _GizmoEventFilter(self)
        self.widget.installEventFilter(self._filter)

    # -- scene ---------------------------------------------------------
    @staticmethod
    def _render_group(sg):
        """Node that is actually rendered. Newer FreeCAD builds return a parent
        separator from getSceneGraph() and ignore children appended after the
        selection root, so attach to the SoFCUnifiedSelection node itself."""
        if sg.getTypeId().getName() == "SoFCUnifiedSelection":
            return sg
        for i in range(sg.getNumChildren()):
            child = sg.getChild(i)
            if child.getTypeId().getName() == "SoFCUnifiedSelection":
                return child
        return sg

    def _build_scene(self):
        L = self.size
        r = L * 0.035
        head_r = L * 0.11
        head_h = L * 0.26
        self.reach = L + head_h
        self._head_h = head_h
        self.k = 1.0                          # handle scale, set while rendering (_on_render)

        # SoAnnotation renders after the scene with depth test off, so the gizmo
        # stays visible even behind semi-transparent geometry
        self.root = coin.SoAnnotation()
        self.switch = coin.SoSwitch()
        self.switch.whichChild.setValue(coin.SO_SWITCH_ALL)
        self.root.addChild(self.switch)

        # Computes the handle scale from the camera of the frame being drawn, so
        # zooming never shows a frame with the old size (no popping).
        self._render_cb = coin.SoCallback()
        self._render_cb.setCallback(self._on_render)
        self.switch.addChild(self._render_cb)

        grp = coin.SoSeparator()
        self.switch.addChild(grp)

        # never let FreeCAD's selection / preselection pick the gizmo
        pick = coin.SoPickStyle()
        pick.style.setValue(coin.SoPickStyle.UNPICKABLE)
        grp.addChild(pick)

        lm = coin.SoLightModel()
        lm.model.setValue(coin.SoLightModel.BASE_COLOR)
        grp.addChild(lm)

        self.tf = coin.SoTransform()
        grp.addChild(self.tf)

        self.color = coin.SoBaseColor()
        self.color.rgb.setValue(*self.COLOR)

        # plane outline (lies in the local XZ plane, local Y = normal)
        outline = coin.SoSeparator()
        grp.addChild(outline)
        outline.addChild(self.color)
        ds = coin.SoDrawStyle()
        ds.lineWidth.setValue(2.0)
        outline.addChild(ds)
        self.coords = coin.SoCoordinate3()
        outline.addChild(self.coords)
        ls = coin.SoIndexedLineSet()
        ls.coordIndex.setValues(0, 6, [0, 1, 2, 3, 0, -1])
        outline.addChild(ls)
        self.set_extents(L, L)

        # rotation rings (world-oriented, centred on the plane origin)
        self.ring_rs = (L * 1.0, L * 1.0)
        rings = coin.SoAnnotation()
        self.switch.addChild(rings)
        rpick = coin.SoPickStyle()
        rpick.style.setValue(coin.SoPickStyle.UNPICKABLE)
        rings.addChild(rpick)
        rlm = coin.SoLightModel()
        rlm.model.setValue(coin.SoLightModel.BASE_COLOR)
        rings.addChild(rlm)
        self.rtf = coin.SoTransform()
        rings.addChild(self.rtf)
        self.ring_scale = coin.SoScale()          # rings are built at k = 1 and scaled here
        rings.addChild(self.ring_scale)
        self.ring_col, self.ring_coords, self.ring_handle = [], [], []
        for k in range(2):
            sep = coin.SoSeparator()
            rings.addChild(sep)
            col = coin.SoBaseColor()
            col.rgb.setValue(*self.RING_COLORS[k])
            sep.addChild(col)
            rds = coin.SoDrawStyle()
            rds.lineWidth.setValue(3.0)
            sep.addChild(rds)
            co = coin.SoCoordinate3()
            sep.addChild(co)
            ln = coin.SoLineSet()
            ln.numVertices.setValue(self.RING_RES + 1)
            sep.addChild(ln)
            ht = coin.SoTransform()
            sep.addChild(ht)
            ball = coin.SoSphere()
            ball.radius.setValue(L * 0.06)
            sep.addChild(ball)
            self.ring_col.append(col)
            self.ring_coords.append(co)
            self.ring_handle.append(ht)

        # arrow, drawn on top of everything
        arrow = coin.SoSeparator()
        grp.addChild(arrow)
        depth = coin.SoDepthBuffer()
        depth.test.setValue(False)
        arrow.addChild(depth)
        self.arrow_scale = coin.SoScale()
        arrow.addChild(self.arrow_scale)
        arrow.addChild(self.color)

        shaft = coin.SoCylinder()
        shaft.radius.setValue(r)
        shaft.height.setValue(2 * L)
        arrow.addChild(shaft)

        for sign in (1, -1):
            sep = coin.SoSeparator()
            t = coin.SoTransform()
            t.translation.setValue(0, sign * (L + head_h / 2), 0)
            if sign < 0:
                t.rotation.setValue(coin.SbRotation(coin.SbVec3f(1, 0, 0), math.pi))
            sep.addChild(t)
            cone = coin.SoCone()
            cone.bottomRadius.setValue(head_r)
            cone.height.setValue(head_h)
            sep.addChild(cone)
            arrow.addChild(sep)

    def _apply_scale(self, k):
        """Scale arrow and rotation handles by k (the plane outline is not scaled)."""
        L = self.size
        self.k = k
        self.arrow_scale.scaleFactor.setValue(k, k, k)
        self.ring_scale.scaleFactor.setValue(k, k, k)
        self.reach = (L + self._head_h) * k
        self.ring_rs = (L * k, L * k)

    def _on_render(self, _data, action):
        """SoCallback: keep the arrow GIZMO_SCREEN_PX pixels long (half length)."""
        if GIZMO_SCREEN_PX <= 0 or not action.isOfType(coin.SoGLRenderAction.getClassTypeId()):
            return
        try:
            state = action.getState()
            h = max(coin.SoViewportRegionElement.get(state).getViewportSizePixels()[1], 1)
            o = self.origin
            world = coin.SoViewVolumeElement.get(state).getWorldToScreenScale(
                coin.SbVec3f(o.x, o.y, o.z), GIZMO_SCREEN_PX / h)
            k = world / max(self.size, 1e-9)
        except Exception:
            return
        if k > 0 and abs(k - self.k) > 1e-4 * self.k:
            self._apply_scale(k)

    def set_extents(self, half_u, half_w):
        self.half_u, self.half_w = half_u, half_w
        pts = [(-half_u, 0, -half_w), (half_u, 0, -half_w),
               (half_u, 0, half_w), (-half_u, 0, half_w)]
        self.coords.point.setValues(0, 4, pts)

    def _ring_defs(self):
        """(axis, first basis direction) of the two rotation rings."""
        return ((self.u_axis, self.normal), (self.fixed_axis, self.u_axis))

    def _ring_point(self, k, deg, R=None):
        a, e1 = self._ring_defs()[k]
        e2 = a.cross(e1)
        t = math.radians(deg)
        R = self.ring_rs[k] if R is None else R
        return e1 * (math.cos(t) * R) + e2 * (math.sin(t) * R)

    def _update_rings(self):
        self.rtf.translation.setValue(self.origin.x, self.origin.y, self.origin.z)
        for k in range(2):
            hd = self.HANDLE_DEG[k]
            pts = []
            for i in range(self.RING_RES + 1):
                v = self._ring_point(k, hd - self.ARC_HALF_DEG + 2 * self.ARC_HALF_DEG * i / self.RING_RES,
                                     self.size)
                pts.append((v.x, v.y, v.z))
            self.ring_coords[k].point.setValues(0, len(pts), pts)
            h = self._ring_point(k, hd, self.size)
            self.ring_handle[k].translation.setValue(h.x, h.y, h.z)

    def set_pose(self, origin, normal, u_axis, fixed_axis=None):
        """origin/normal/u_axis are App.Vector; local X -> u, local Y -> normal."""
        if fixed_axis is not None:
            self.fixed_axis = App.Vector(fixed_axis)
        self.normal = App.Vector(normal)
        n = App.Vector(normal)
        u = App.Vector(u_axis)
        w = u.cross(n)
        self.u_axis, self.w_axis = u, w
        m = App.Matrix()
        m.A11, m.A21, m.A31 = u.x, u.y, u.z
        m.A12, m.A22, m.A32 = n.x, n.y, n.z
        m.A13, m.A23, m.A33 = w.x, w.y, w.z
        q = App.Rotation(m).Q
        self.tf.rotation.setValue(coin.SbRotation(q[0], q[1], q[2], q[3]))
        self._set_origin(origin)

    def _set_origin(self, origin):
        self.origin = App.Vector(origin)
        self.tf.translation.setValue(origin.x, origin.y, origin.z)
        self._update_rings()

    def set_visible(self, flag):
        self.switch.whichChild.setValue(coin.SO_SWITCH_ALL if flag else coin.SO_SWITCH_NONE)

    def is_visible(self):
        return self.switch.whichChild.getValue() != coin.SO_SWITCH_NONE

    # -- picking math (x, y: widget pixels, origin top-left) ------------
    def _volume(self):
        rm = self.viewer.getSoRenderManager()
        vp = rm.getViewportRegion()
        return rm.getCamera().getViewVolume(vp.getViewportAspectRatio())

    def _squeeze(self):
        """In a portrait viewport Coin shrinks the picture by width/height (ADJUST_CAMERA);
        the view volume does not include that, so it is applied here."""
        rm = self.viewer.getSoRenderManager()
        return min(rm.getViewportRegion().getViewportAspectRatio(), 1.0)

    def _norm(self, x, y):
        a = max(self._squeeze(), 1e-3)
        nx = x / max(self.widget.width(), 1)
        ny = 1.0 - y / max(self.widget.height(), 1)
        return coin.SbVec2f(0.5 + (nx - 0.5) / a, 0.5 + (ny - 0.5) / a)

    def _scr(self, p, vv=None):
        """World point -> widget pixels (origin top-left)."""
        vv = vv or self._volume()
        s = vv.projectToScreen(coin.SbVec3f(p.x, p.y, p.z)).getValue()
        a = self._squeeze()
        return ((0.5 + (s[0] - 0.5) * a) * self.widget.width(),
                (1.0 - (0.5 + (s[1] - 0.5) * a)) * self.widget.height())

    @staticmethod
    def _dist_to_segment(x, y, a, b):
        dx, dy = b[0] - a[0], b[1] - a[1]
        seg2 = dx * dx + dy * dy
        t = 0.0 if seg2 < 1e-6 else max(0.0, min(1.0, ((x - a[0]) * dx + (y - a[1]) * dy) / seg2))
        return math.hypot(x - (a[0] + t * dx), y - (a[1] + t * dy))

    @staticmethod
    def _inside_polygon(x, y, pts):
        """Point in convex polygon (screen space)."""
        sign = 0
        for i in range(len(pts)):
            a, b = pts[i], pts[(i + 1) % len(pts)]
            cross = (b[0] - a[0]) * (y - a[1]) - (b[1] - a[1]) * (x - a[0])
            if abs(cross) < 1e-9:
                continue
            s_ = 1 if cross > 0 else -1
            if sign == 0:
                sign = s_
            elif s_ != sign:
                return False
        return True

    def hit_ring(self, x, y):
        """Index of the rotation handle (ball) under the pixel, or None."""
        if self.on_rot_drag is None or not self.is_visible():
            return None
        vv = self._volume()
        w, h = self.widget.width(), self.widget.height()
        best, best_d = None, self.PICK_PIXELS * 0.8
        for k in range(2):
            p = self.origin + self._ring_point(k, self.HANDLE_DEG[k])
            sx, sy = self._scr(p, vv)
            d = math.hypot(x - sx, y - sy)
            if d < best_d:
                best, best_d = k, d
        return best

    def _ring_angle(self, x, y, grazing_ok=False):
        """Angle (rad) of the mouse ray hit on the ring plane, in the grabbed basis."""
        a, e1, e2 = self._rot["basis"]
        p0, p1 = self._volume().projectPointToLine(self._norm(x, y))
        q0 = App.Vector(*p0.getValue())
        d = App.Vector(*p1.getValue()) - q0
        den = d.dot(a)
        if abs(den) < (1e-6 if grazing_ok else 0.25) * max(d.Length, 1e-9):
            return None
        t = (self._rot["center"] - q0).dot(a) / den
        v = q0 + d * t - self._rot["center"]
        return math.atan2(v.dot(e2), v.dot(e1))

    def _start_tangent(self, x, y):
        """Edge-on ring: map mouse motion along the ring's screen tangent to an angle."""
        a, e1, e2 = self._rot["basis"]
        vv = self._volume()
        w, h = self.widget.width(), self.widget.height()
        R = self.ring_rs[self._rot["k"]]
        c = self._rot["center"]

        def scr(t):
            return self._scr(c + e1 * (math.cos(t) * R) + e2 * (math.sin(t) * R), vv)

        best_t = math.radians(self.HANDLE_DEG[self._rot["k"]])
        h_ = 0.05
        (ax, ay), (bx, by) = scr(best_t - h_), scr(best_t + h_)
        L = math.hypot(bx - ax, by - ay)
        if L < 1e-3:
            L = 1.0
            bx, by, ax, ay = 1.0, 0.0, 0.0, 0.0
        self._rot["tan"] = ((bx - ax) / L, (by - ay) / L, max(L / (2 * h_), 1e-3), x, y)

    def _set_ring_hot(self, k, flag):
        for i in range(2):
            on = flag and i == k
            self.ring_col[i].rgb.setValue(*(self.RING_HOT[i] if on else self.RING_COLORS[i]))

    def hit_test(self, x, y):
        vv = self._volume()
        w, h = self.widget.width(), self.widget.height()

        def to_px(p):
            return self._scr(p, vv)

        # arrow
        a = to_px(self.origin - self.normal * self.reach)
        b = to_px(self.origin + self.normal * self.reach)
        if self._dist_to_segment(x, y, a, b) <= self.PICK_PIXELS:
            return True

        if not GIZMO_PICK_PLANE:
            return False

        # plane: outline band and surface
        u = self.u_axis * self.half_u
        v = self.w_axis * self.half_w
        o = self.origin
        corners = [to_px(o - u - v), to_px(o + u - v), to_px(o + u + v), to_px(o - u + v)]
        if self._inside_polygon(x, y, corners):
            return True
        return any(
            self._dist_to_segment(x, y, corners[i], corners[(i + 1) % 4]) <= self.PICK_PIXELS * 0.6
            for i in range(4)
        )

    def _axis_param(self, x, y, anchor):
        """t of the axis point (anchor + t*normal) closest to the mouse ray."""
        p0, p1 = self._volume().projectPointToLine(self._norm(x, y))
        q0 = App.Vector(*p0.getValue())
        d = App.Vector(*p1.getValue()) - q0
        n = self.normal
        w0 = anchor - q0
        b = n.dot(d)
        c = d.dot(d)
        denom = c - b * b            # n.n == 1
        if abs(denom) < 1e-9 * max(c, 1.0):
            return None              # looking straight along the axis
        return (b * d.dot(w0) - c * n.dot(w0)) / denom

    def _set_hot(self, flag):
        if flag != self.hot:
            self.hot = flag
            self.color.rgb.setValue(*(self.COLOR_HOT if flag else self.COLOR))

    # -- Qt events -----------------------------------------------------
    @staticmethod
    def _pos(ev):
        p = ev.position() if hasattr(ev, "position") else ev.pos()
        return p.x(), p.y()

    def handle_qt_event(self, ev):
        """Returns True when the event was consumed."""
        if self._removed:
            return False
        et = ev.type()

        if et == QEvent.MouseButtonPress:
            if ev.button() != Qt.LeftButton or ev.modifiers() != Qt.NoModifier:
                return False
            if not self.is_visible():
                return False
            x, y = self._pos(ev)
            k = self.hit_ring(x, y)
            if k is not None:
                a, e1 = self._ring_defs()[k]
                self._rot = {"k": k, "center": App.Vector(self.origin),
                             "basis": (App.Vector(a), App.Vector(e1), a.cross(e1)), "last": None,
                             "total": 0.0}
                ang = self._ring_angle(x, y)
                if ang is None:
                    self._start_tangent(x, y)          # ring seen edge-on: drag along its screen tangent
                else:
                    self._rot["last"] = ang
                self.rot_active = k
                self._set_ring_hot(k, True)
                self.on_rot_start(k)
                return True
            if not self.hit_test(x, y):
                return False
            t = self._axis_param(x, y, self.origin)
            if t is None:
                return False
            self.dragging = True
            self._anchor = App.Vector(self.origin)
            self._grab_t = t
            self._set_hot(True)
            self.on_start()
            return True

        if et == QEvent.MouseMove:
            x, y = self._pos(ev)
            if self.rot_active is not None:
                if "tan" in self._rot:
                    tx, ty, ppr, x0, y0 = self._rot["tan"]
                    self._rot["total"] = ((x - x0) * tx + (y - y0) * ty) / ppr
                    self.on_rot_drag(self.rot_active, math.degrees(self._rot["total"]))
                    return True
                ang = self._ring_angle(x, y)
                if ang is not None:
                    dlt = ang - self._rot["last"]
                    dlt = (dlt + math.pi) % (2 * math.pi) - math.pi      # unwrap
                    self._rot["last"] = ang
                    self._rot["total"] += dlt
                    self.on_rot_drag(self.rot_active, math.degrees(self._rot["total"]))
                return True
            if self.dragging:
                t = self._axis_param(x, y, self._anchor)
                if t is not None:
                    applied = self.on_drag(t - self._grab_t)
                    self._set_origin(self._anchor + self.normal * applied)
                return True
            if self.is_visible() and not ev.buttons():
                self._set_hot(self.hit_test(x, y))
                self._set_ring_hot(self.hit_ring(x, y), True) if self.hit_ring(x, y) is not None \
                    else self._set_ring_hot(-1, False)
            return False

        if et == QEvent.MouseButtonRelease and self.rot_active is not None:
            self.rot_active = None
            self._rot = None
            self._set_ring_hot(-1, False)
            self.on_rot_end()
            return True

        if et == QEvent.MouseButtonRelease and self.dragging:
            self.dragging = False
            self._set_hot(False)
            self.on_end()
            return True

        return False

    # -- cleanup -------------------------------------------------------
    def remove(self):
        if self._removed:
            return
        self._removed = True
        self.dragging = False
        try:
            self.widget.removeEventFilter(self._filter)
        except Exception:
            pass
        try:
            self.sg.removeChild(self.root)
        except Exception:
            pass


def _hide_in_tree(feat):
    """Keep a helper object out of the tree view; big documents stay readable."""
    try:
        feat.ViewObject.ShowInTree = False
    except Exception:
        pass                  # older FreeCAD: the object just stays listed


class _Collapsible(QWidget):
    """A titled section that can be folded to keep the panel short."""

    def __init__(self, title, expanded=True):
        super().__init__()
        outer = QVBoxLayout(self)
        outer.setContentsMargins(0, 0, 0, 0)
        outer.setSpacing(2)

        self._title = title
        self.toggle = QToolButton()
        self.toggle.setStyleSheet("QToolButton { border: none; font-weight: bold; }")
        self.toggle.setToolButtonStyle(Qt.ToolButtonTextOnly)
        self.toggle.setSizePolicy(QSizePolicy.Expanding, QSizePolicy.Fixed)
        self.toggle.setCheckable(True)
        self.toggle.setChecked(expanded)
        self.toggle.clicked.connect(self._apply)
        outer.addWidget(self.toggle)

        self.body = QWidget()
        self.body_layout = QVBoxLayout(self.body)
        self.body_layout.setContentsMargins(6, 0, 0, 4)
        outer.addWidget(self.body)

        line = QFrame()
        line.setFrameShape(QFrame.HLine)
        line.setFrameShadow(QFrame.Sunken)
        outer.addWidget(line)
        self._apply()

    def _apply(self, *args):
        on = self.toggle.isChecked()
        self.toggle.setText(("\u25BE " if on else "\u25B8 ") + self._title)
        self.body.setVisible(on)


class SectionTaskPanel:
    """Adapter that shows the options in FreeCAD's Tasks panel."""

    def __init__(self, owner, widget):
        self.owner = owner
        self.form = widget

    def getStandardButtons(self):
        btn = QDialogButtonBox.Close
        try:
            return int(btn)           # PySide2
        except TypeError:
            return btn.value          # PySide6 (enum flag)

    def reject(self):
        self.owner.shutdown(close_dialog=False)
        return True

    accept = reject

    def isAllowedAlterSelection(self):
        return True

    def isAllowedAlterView(self):
        return True

    def isAllowedAlterDocument(self):
        return True


class _SceneObserver:
    """Document observer: flags placement / shape changes of scene objects."""

    PROPS = ("Placement", "Shape", "LinkPlacement", "LinkedObject", "Group")

    def __init__(self, owner):
        self.owner = owner

    def slotDeletedDocument(self, doc):
        try:
            if doc.Name == self.owner._doc_name:
                self.owner.on_document_closed()
        except Exception:
            pass

    def slotChangedObject(self, obj, prop):
        try:
            if prop not in self.PROPS or obj.Name.startswith(("Live_", "Section_")):
                return
            self.owner.on_scene_changed()
        except Exception:
            pass


class _Target:
    """One object of the scene: its global shape and (when sectioned) its copy."""

    def __init__(self, obj, shape, checked=False):
        self.obj = obj
        self.shape = shape
        self.checked = checked
        self.key = (obj.Document.Name, obj.Name)
        self.label = obj.Label
        self.color = LiveSectionAnalyzer._display_color(obj)
        self.bbox = shape.BoundBox
        self.slice_ms = 0.0         # duration of the last exact slice
        self.mesh = None            # (vertices, triangles) numpy arrays, built on demand
        self.meshes = {}            # welded meshes for the mesh section: 0 = coarse, 1 = fine
        self.plane_index = {}       # fine -> (vertices, normal, mesh_plane_index()), see _plane_index
        self.bg_feat = None
        self.bg_mode = None
        self.was_visible = True
        self.saved_look = None      # the object's own look while GPU clipping tints it
        self.src = None             # (top object, subname) when picked from the selection


class _SceneMixin:
    """Finding the objects to section and following them when they move."""

    # ------------------------------------------------------------------
    # Setup
    # ------------------------------------------------------------------
    # Selected objects that only hold other objects: the part to section is the
    # first child in the selection path.
    _CONTAINERS = ("App::Part", "Assembly::AssemblyObject", "Assembly::AssemblyLink",
                   "App::LinkGroup", "App::DocumentObjectGroup")

    @staticmethod
    def _union_bbox(shapes):
        bb = App.BoundBox()
        for sh in shapes:
            bb.add(sh.BoundBox)
        return bb

    @staticmethod
    def _solid_or_compound(shape):
        if shape.ShapeType == "Compound" and len(shape.Solids) == 1:
            return shape.Solids[0]
        return shape

    def _resolve_entry(self, top, sub):
        """Selection entry -> (display object, shape in GLOBAL coordinates).

        getSelection() returns the leaf object (e.g. a Pocket inside a linked
        Body), whose shape lacks the placement of the assembly / link / part it
        sits in. With the full path, Part.getShape() applies every placement.
        """
        shape = None
        try:
            shape = Part.getShape(top, sub, needSubElement=False, refine=False)
        except Exception:
            pass
        if shape is None or shape.isNull():
            if hasattr(top, "Shape") and not top.Shape.isNull():
                shape = top.Shape
            else:
                return None, None

        # The object that gets hidden while the section is shown
        target = top
        if sub and top.TypeId in self._CONTAINERS:
            try:
                first = top.resolve(sub.split(".")[0] + ".")[0]
                if first is not None:
                    target = first
            except Exception:
                pass
        if target is not top or top.getParentGeoFeatureGroup() is not None:
            try:
                return target, self._global_shape(target)
            except Exception:
                pass
        return target, self._solid_or_compound(shape)

    def _global_shape(self, obj):
        """Shape of a scene object with the placements of all its parents.

        The parent placements are multiplied here instead of resolving a subname
        path with Part.getShape(): for parts inside an Assembly::AssemblyLink that
        path ignores the link's own placement (moved sub-assemblies left their
        section behind). Only the Location changes, so the TShape is shared and a
        pure move is cheap to detect (see _rigid_delta).
        """
        shape = Part.getShape(obj, needSubElement=False, refine=False)
        cur = obj
        while True:
            try:
                parent = cur.getParentGeoFeatureGroup()
            except Exception:
                parent = None
            if parent is None:
                break
            pl = getattr(parent, "Placement", None)
            if pl is not None:
                shape.Placement = pl.multiply(shape.Placement)
            cur = parent
        return self._solid_or_compound(shape)

    def _scene_targets(self, skip_keys=()):
        """Visible solids of the active document (not the macro's own objects)."""
        found = []
        doc = App.ActiveDocument
        if not doc:
            return found
        for obj in doc.Objects:
            try:
                if obj.Name.startswith(("Live_", "Section_")) or obj.TypeId in self._CONTAINERS:
                    continue
                vo = obj.ViewObject
                if vo is None or not hasattr(obj, "Shape") or not vo.Visibility:
                    continue
                if (obj.Document.Name, obj.Name) in skip_keys:
                    continue
                parent = obj.getParentGeoFeatureGroup()
                if parent is not None and parent.TypeId == "PartDesign::Body":
                    continue                      # features inside a Body: the Body is listed
                hidden_parent = False
                while parent is not None:
                    if parent.ViewObject is not None and not parent.ViewObject.Visibility:
                        hidden_parent = True
                        break
                    parent = parent.getParentGeoFeatureGroup()
                if hidden_parent:
                    continue
                shape = self._global_shape(obj)
                if shape.isNull() or not shape.Solids:
                    continue
                found.append(_Target(obj, shape))
            except Exception:
                continue
        found.sort(key=lambda t: t.label.lower())
        return found

    def _collect_targets(self):
        """Selected objects (checked) + every other visible solid (unchecked)."""
        picked, seen = [], set()
        for sel in Gui.Selection.getSelectionEx("", 0):
            for sub in (sel.SubElementNames or [""]):
                obj, shape = self._resolve_entry(sel.Object, sub)
                if obj is None:
                    continue
                key = (obj.Document.Name, obj.Name)
                if key in seen:
                    continue
                seen.add(key)
                t = _Target(obj, shape, checked=True)
                t.src = (sel.Object, sub)
                picked.append(t)
        scene = self._scene_targets(skip_keys=seen)
        if not picked:
            # Nothing selected: clip everything that is visible. A small scene is
            # sectioned completely, a big one starts unchecked (check what you need).
            if not scene:
                QMessageBox.warning(None, "Error", "There are no visible solids in the active document.")
                return False
            if len(scene) <= AUTO_SECTION_MAX_OBJECTS:
                for t in scene:
                    t.checked = True
        self.targets = picked + scene
        return True

    def rescan_objects(self):
        """Re-read the visible solids; keeps the objects that are being sectioned."""
        if self._closed:
            return
        kept = [t for t in self.targets if t.checked]
        keys = {t.key for t in kept}
        dropped = [t for t in self.targets if not t.checked]
        for t in dropped:
            self._restore_transparency(t)
            self._release(t)
        self.targets = kept + self._scene_targets(skip_keys=keys)
        self._fill_list()
        self.schedule_update()

    @staticmethod
    def _display_color(obj):
        """Shape color of an object, following links to the real object."""
        candidates = [obj, getattr(obj, "LinkedObject", None)]
        try:
            candidates.append(obj.getLinkedObject(True))
        except Exception:
            pass
        for o in candidates:
            vo = getattr(o, "ViewObject", None) if o is not None else None
            color = getattr(vo, "ShapeColor", None) if vo is not None else None
            if color:
                return color
        return (0.8, 0.8, 0.8)

    # ------------------------------------------------------------------
    # Following moving parts
    # ------------------------------------------------------------------
    def on_scene_changed(self):
        if self._closed or not FOLLOW_SCENE:
            return
        self._scene_dirty = True
        self.schedule_update()

    def _current_shape(self, t):
        if t.src is not None:
            return self._resolve_entry(*t.src)[1]
        return self._global_shape(t.obj)

    @staticmethod
    def _rigid_delta(old, new):
        """4x4 numpy matrix that moves `old` onto `new`, or None if the geometry changed."""
        if new.isPartner(old):
            return np.array(new.Matrix.A).reshape(4, 4) @ np.linalg.inv(np.array(old.Matrix.A).reshape(4, 4))
        a, b = old.Vertexes, new.Vertexes
        if len(a) != len(b) or len(old.Faces) != len(new.Faces) or not a:
            return None
        if abs(old.Volume - new.Volume) > 1e-6 * max(abs(old.Volume), 1.0):
            return None
        step = max(1, len(a) // 2000)
        P = np.array([(v.X, v.Y, v.Z) for v in a[::step]])
        Q = np.array([(v.X, v.Y, v.Z) for v in b[::step]])
        # rigid fit (Kabsch); topology order is kept when a shape is only moved
        pc, qc = P.mean(axis=0), Q.mean(axis=0)
        U, _, Wt = np.linalg.svd((P - pc).T @ (Q - qc))
        D = np.diag([1.0, 1.0, np.sign(np.linalg.det(Wt.T @ U.T))])
        R = Wt.T @ D @ U.T
        tr = qc - R @ pc
        diag = max(old.BoundBox.DiagonalLength, 1e-9)
        if np.abs(P @ R.T + tr - Q).max() > 1e-6 * diag:
            return None
        M = np.eye(4)
        M[:3, :3], M[:3, 3] = R, tr
        return M

    def _forget(self, t):
        """Drop every cached section of one target."""
        for cache in (self._slice_cache, self._loop_cache, self._tri_cache):
            for k in [k for k in cache if k[0] == t.key]:
                del cache[k]

    def _refresh_targets(self):
        """Re-read the global shapes; moved meshes are transformed, changed ones rebuilt.
        Returns True if anything moved or changed."""
        changed = False
        for t in self.targets:
            try:
                new = self._current_shape(t)
            except Exception:
                continue
            if new is None or new.isNull() or new.isSame(t.shape):
                continue
            M = self._rigid_delta(t.shape, new) if HAS_NP else None
            if M is not None and np.allclose(M, np.eye(4), atol=1e-12):
                t.shape = new
                continue
            if M is not None:
                R, tr = M[:3, :3], M[:3, 3]
                t.meshes = {lvl: (V @ R.T + tr, T, gap) for lvl, (V, T, gap) in t.meshes.items()}
                if t.mesh is not None:
                    t.mesh = (t.mesh[0] @ R.T + tr, t.mesh[1])
            else:
                t.meshes, t.mesh, t.slice_ms = {}, None, 0.0
            t.shape = new
            t.bbox = new.BoundBox
            t.bg_mode = None                # boolean background: cut again
            self._forget(t)
            changed = True
        return changed



class _PanelMixin:
    """Options panel, its event handlers, gizmo callbacks and styles."""

    def init_ui(self):
        content = QWidget()
        root = QVBoxLayout(content)
        root.setContentsMargins(4, 4, 4, 4)

        # --- HEADER: logo, title, version ---
        header = QHBoxLayout()
        pm = _logo_pixmap(32)
        if pm is not None:
            logo = QLabel()
            logo.setPixmap(pm)
            logo.setFixedSize(36, 36)
            header.addWidget(logo)
        title = QLabel(
            "<b>Live Section Analyzer</b><br>"
            "<span style='color: #777; font-size: 10px;'>v%s</span>" % VERSION
        )
        header.addWidget(title, 1)
        self.btn_toolbar = QToolButton()
        self.btn_toolbar.setAutoRaise(True)
        self.btn_toolbar.clicked.connect(self.toggle_toolbar)
        self._sync_toolbar_button()
        header.addWidget(self.btn_toolbar)
        root.addLayout(header)

        def section(title, expanded=True):
            box = _Collapsible(title, expanded)
            root.addWidget(box)
            return box.body_layout

        # --- OBJECTS ---
        layout = section("Objects (checked = section)")
        self.obj_list = QListWidget()
        self.obj_list.setMinimumHeight(110)
        self.obj_list.setToolTip(
            "Everything visible is clipped by the plane.\n"
            "Checked objects also get a section fill, outline and hatch."
        )
        layout.addWidget(self.obj_list)
        row = QHBoxLayout()
        for text, slot in (("All", lambda: self._check_all(True)),
                           ("None", lambda: self._check_all(False)),
                           ("Refresh", self.rescan_objects)):
            b = QPushButton(text)
            b.setMinimumWidth(0)
            b.clicked.connect(slot)
            row.addWidget(b)
        layout.addLayout(row)
        self._fill_list()
        self.obj_list.itemChanged.connect(self.on_target_toggled)

        # --- SECTION PLANE ---
        layout = section("Section Plane")
        plane_layout = QHBoxLayout()
        plane_layout.addWidget(QLabel("Plane:"))
        self.combo_plane = QComboBox()
        self.combo_plane.addItems(["XY", "XZ", "YZ"])
        self.combo_plane.setCurrentText("YZ")
        plane_layout.addWidget(self.combo_plane, 1)
        layout.addLayout(plane_layout)

        self.chk_gizmo = QCheckBox("Show plane gizmo")
        self.chk_gizmo.setToolTip("Drag the arrow in the 3D view to move the plane")
        self.chk_gizmo.setChecked(True)
        self.chk_gizmo.stateChanged.connect(self.on_gizmo_toggled)
        layout.addWidget(self.chk_gizmo)

        # Tilt: turns the plane about its two in-plane axes (0 / 0 = axis-aligned)
        tilt_layout = QHBoxLayout()
        self.lbl_tilt_a, self.lbl_tilt_b = QLabel("Tilt A:"), QLabel("Tilt B:")
        self.spin_tilt_a, self.spin_tilt_b = QDoubleSpinBox(), QDoubleSpinBox()
        for lbl, sp in ((self.lbl_tilt_a, self.spin_tilt_a), (self.lbl_tilt_b, self.spin_tilt_b)):
            sp.setRange(-89.0, 89.0)
            sp.setDecimals(1)
            sp.setSingleStep(5.0)
            sp.setSuffix(" \u00b0")
            sp.setToolTip("Tilts the section plane about one of its in-plane axes. "
                          "0 \u00b0 / 0 \u00b0 is the plain XY / XZ / YZ plane.")
            sp.valueChanged.connect(self.schedule_update)
            tilt_layout.addWidget(lbl)
            tilt_layout.addWidget(sp)
        self.btn_tilt_reset = QPushButton("Reset")
        self.btn_tilt_reset.setMinimumWidth(0)
        self.btn_tilt_reset.setToolTip("Back to the axis-aligned plane")
        self.btn_tilt_reset.clicked.connect(self.reset_tilt)
        tilt_layout.addWidget(self.btn_tilt_reset)
        layout.addLayout(tilt_layout)

        # Section engine (part of the Section Plane group)
        mesh_ok = HAS_NP and self.mesh_switch is not None
        self.chk_mesh = QCheckBox("Mesh-based section")
        self.chk_mesh.setChecked(bool(MESH_SECTION) and mesh_ok)
        self.chk_mesh.setEnabled(mesh_ok)
        self.chk_mesh.setToolTip(
            "Builds outline, hatch and fill from the tessellation instead of OpenCascade: "
            "much faster on big or curved parts, but curves are polygonal. Each object gets its own hatch angle and "
            "spacing. Freeze Section always uses exact geometry."
        )
        layout.addWidget(self.chk_mesh)

        # Offset (part of the Section Plane group)
        max_dim = max(self.x_len, self.y_len, self.z_len)
        self.offset_range = max(max_dim * 0.6, 10.0)

        offset_layout = QHBoxLayout()
        offset_layout.addWidget(QLabel("Offset:"))

        self.slider = QSlider(Qt.Horizontal)
        self.slider.setRange(-100, 100)
        self.slider.setValue(0)
        self.slider.setTickPosition(QSlider.TicksBelow)
        self.slider.setTickInterval(10)
        offset_layout.addWidget(self.slider)

        self.offset_spin = QDoubleSpinBox()
        self.offset_spin.setRange(-self.offset_range, self.offset_range)
        self.offset_spin.setValue(0.0)
        self.offset_spin.setSingleStep(self.offset_range / 20.0)
        self.offset_spin.setSuffix(" mm")
        self.offset_spin.setDecimals(1)
        self.offset_spin.setMaximumWidth(100)
        offset_layout.addWidget(self.offset_spin)

        layout.addLayout(offset_layout)

        range_label = QLabel(f"<i>Range: ±{self.offset_range:.1f} mm</i>")
        range_label.setStyleSheet("color: #666; font-size: 10px;")
        range_label.setToolTip("Based on the object size")
        layout.addWidget(range_label)

        # Background (part of the Section Plane group)
        trans_layout = QHBoxLayout()
        trans_layout.addWidget(QLabel("Transparency (%):"))
        self.spin_trans = QSpinBox()
        self.spin_trans.setRange(0, 100)
        self.spin_trans.setValue(0)
        trans_layout.addWidget(self.spin_trans)
        trans_layout.addStretch()
        layout.addLayout(trans_layout)

        # GPU clip toggle
        gpu_layout = QHBoxLayout()
        self.chk_gpu_clip = QCheckBox("Fast GPU clipping")
        self.chk_gpu_clip.setChecked(self.clip_ok)
        self.chk_gpu_clip.setEnabled(self.clip_ok)
        self.chk_gpu_clip.setToolTip(
            "Clips the object on the GPU (fast). When off, an exact boolean "
            "cut is computed instead (slower, but real geometry)."
        )
        gpu_layout.addWidget(self.chk_gpu_clip)
        gpu_layout.addStretch()
        layout.addLayout(gpu_layout)

        mirror_layout = QHBoxLayout()
        self.chk_mirror_bg = QCheckBox("Mirror Background")
        self.chk_mirror_bg.setToolTip("Show the opposite half")
        self.chk_mirror_bg.setChecked(False)
        mirror_layout.addWidget(self.chk_mirror_bg)
        mirror_layout.addStretch()
        layout.addLayout(mirror_layout)

        # --- SECTION FILL ---
        layout = section("Section Fill", expanded=False)

        # With GPU clipping the cut is open, so the fill acts as the cap: default on.
        self.chk_section_fill = QCheckBox("Show Section Fill")
        self.chk_section_fill.setChecked(True)
        layout.addWidget(self.chk_section_fill)

        self.chk_obj_colors = QCheckBox("Use object colors")
        self.chk_obj_colors.setChecked(sum(1 for t in self.targets if t.checked) > 1)
        self.chk_obj_colors.setToolTip("Tint each object's section with its own color")
        layout.addWidget(self.chk_obj_colors)

        fill_color_layout = QHBoxLayout()
        fill_color_layout.addWidget(QLabel("Color:"))
        self.fill_color_btn = QPushButton()
        self.fill_color_btn.setStyleSheet("background-color: rgb(191, 166, 173); max-width: 50px;")
        self.fill_color_btn.clicked.connect(lambda: self.pick_color(self.fill_color_btn, "fill"))
        fill_color_layout.addWidget(self.fill_color_btn)
        fill_color_layout.addStretch()
        layout.addLayout(fill_color_layout)

        # --- EDGE LINE SETTINGS ---
        layout = section("Edge Lines", expanded=False)

        self.chk_edges = QCheckBox("Show Edge Lines")
        self.chk_edges.setChecked(True)
        layout.addWidget(self.chk_edges)

        edge_color_layout = QHBoxLayout()
        edge_color_layout.addWidget(QLabel("Color:"))
        self.edge_color_btn = QPushButton()
        self.edge_color_btn.setStyleSheet("background-color: rgb(0, 0, 0); max-width: 50px;")
        self.edge_color_btn.clicked.connect(lambda: self.pick_color(self.edge_color_btn, "edge"))
        edge_color_layout.addWidget(self.edge_color_btn)
        edge_color_layout.addStretch()
        layout.addLayout(edge_color_layout)

        edge_width_layout = QHBoxLayout()
        edge_width_layout.addWidget(QLabel("Width:"))
        self.edge_width_spin = QDoubleSpinBox()
        self.edge_width_spin.setRange(0.5, 10.0)
        self.edge_width_spin.setValue(2.0)
        self.edge_width_spin.setSingleStep(0.5)
        edge_width_layout.addWidget(self.edge_width_spin)
        edge_width_layout.addStretch()
        layout.addLayout(edge_width_layout)

        # --- HATCH SETTINGS ---
        layout = section("Hatch", expanded=False)

        self.chk_hatch = QCheckBox("Enable Hatch")
        self.chk_hatch.setChecked(True)
        layout.addWidget(self.chk_hatch)

        spacing_layout = QHBoxLayout()
        spacing_layout.addWidget(QLabel("Spacing (mm):"))
        self.spin_spacing = QDoubleSpinBox()
        self.spin_spacing.setRange(0.5, 500.0)
        self.spin_spacing.setValue(3.0)
        self.spin_spacing.setSingleStep(0.5)
        spacing_layout.addWidget(self.spin_spacing)
        spacing_layout.addStretch()
        layout.addLayout(spacing_layout)

        hatch_color_layout = QHBoxLayout()
        hatch_color_layout.addWidget(QLabel("Color:"))
        self.hatch_color_btn = QPushButton()
        self.hatch_color_btn.setStyleSheet("background-color: rgb(77, 77, 77); max-width: 50px;")
        self.hatch_color_btn.clicked.connect(lambda: self.pick_color(self.hatch_color_btn, "hatch"))
        hatch_color_layout.addWidget(self.hatch_color_btn)
        hatch_color_layout.addStretch()
        layout.addLayout(hatch_color_layout)

        hatch_width_layout = QHBoxLayout()
        hatch_width_layout.addWidget(QLabel("Width:"))
        self.hatch_width_spin = QDoubleSpinBox()
        self.hatch_width_spin.setRange(0.5, 5.0)
        self.hatch_width_spin.setValue(1.0)
        self.hatch_width_spin.setSingleStep(0.5)
        hatch_width_layout.addWidget(self.hatch_width_spin)
        hatch_width_layout.addStretch()
        layout.addLayout(hatch_width_layout)

        hatch_point_layout = QHBoxLayout()
        hatch_point_layout.addWidget(QLabel("Point Size (px):"))
        self.hatch_point_spin = QSpinBox()
        self.hatch_point_spin.setRange(0, 10)
        self.hatch_point_spin.setValue(1)
        self.hatch_point_spin.setSingleStep(1)
        hatch_point_layout.addWidget(self.hatch_point_spin)
        hatch_point_layout.addStretch()
        layout.addLayout(hatch_point_layout)

        # --- FREEZE BUTTON ---
        self.btn_freeze = QPushButton("❄️ Freeze Section")
        self.btn_freeze.setToolTip("Simple copy of the section, in its own folder")
        self.btn_freeze.setStyleSheet("""
            QPushButton {
                background-color: #4CAF50;
                color: white;
                font-weight: bold;
                padding: 8px;
                border-radius: 4px;
            }
            QPushButton:hover {
                background-color: #45a049;
            }
        """)
        self.btn_freeze.clicked.connect(self.freeze_section)

        # --- CONNECTIONS ---
        self.combo_plane.currentIndexChanged.connect(self.schedule_update)

        self.slider.valueChanged.connect(self.on_slider_changed)
        self.slider.sliderReleased.connect(self.schedule_update)   # full update after drag
        self.offset_spin.valueChanged.connect(self.on_spin_changed)

        # Geometry-affecting controls -> debounced geometry update
        self.chk_mirror_bg.stateChanged.connect(self.schedule_update)
        self.chk_gpu_clip.stateChanged.connect(self.schedule_update)
        self.chk_section_fill.stateChanged.connect(self.schedule_update)
        self.chk_obj_colors.stateChanged.connect(self.schedule_update)
        self.chk_hatch.stateChanged.connect(self.schedule_update)
        self.spin_spacing.valueChanged.connect(self.schedule_update)
        self.chk_edges.stateChanged.connect(self.schedule_update)
        self.chk_mesh.stateChanged.connect(self.schedule_update)

        # Style-only controls -> cheap style update (no geometry)
        self.spin_trans.valueChanged.connect(self.update_style)
        self.edge_width_spin.valueChanged.connect(self.update_style)
        self.hatch_width_spin.valueChanged.connect(self.update_style)
        self.hatch_point_spin.valueChanged.connect(self.update_style)

        root.addStretch()

        # Scrollable options + a footer that is always visible
        scroll = QScrollArea()
        scroll.setWidgetResizable(True)
        scroll.setFrameShape(QFrame.NoFrame)
        scroll.setHorizontalScrollBarPolicy(Qt.ScrollBarAlwaysOff)
        scroll.setWidget(content)

        panel = QWidget()
        panel_layout = QVBoxLayout(panel)
        panel_layout.setContentsMargins(0, 0, 0, 0)
        panel_layout.addWidget(scroll, 1)

        # Hint shown while more options are hidden below the visible area
        bar = scroll.verticalScrollBar()
        self.more_hint = QPushButton("\u25BC  more options below  \u25BC")
        self.more_hint.setFlat(True)
        self.more_hint.setCursor(Qt.PointingHandCursor)
        self.more_hint.setToolTip("Scroll down")
        self.more_hint.setStyleSheet(
            "QPushButton { color: #c0392b; font-weight: bold; border: none; padding: 3px; }"
            "QPushButton:hover { text-decoration: underline; }"
        )
        self.more_hint.clicked.connect(lambda: bar.setValue(bar.maximum()))

        def update_hint(*args):
            self.more_hint.setVisible(bar.maximum() > 0 and bar.value() < bar.maximum() - 4)

        bar.valueChanged.connect(update_hint)
        bar.rangeChanged.connect(update_hint)
        self.more_hint.setVisible(False)
        panel_layout.addWidget(self.more_hint)

        panel_layout.addWidget(self.btn_freeze)

        # In the Tasks panel the standard "Close" button is used instead.
        self.btn_close = QPushButton("Close Analysis")
        self.btn_close.clicked.connect(self.close)
        panel_layout.addWidget(self.btn_close)
        self.panel = panel

    def _sync_toolbar_button(self):
        try:
            on = toolbar_installed()
        except Exception:
            on = False
        self.btn_toolbar.setText("− Toolbar" if on else "+ Toolbar")
        self.btn_toolbar.setToolTip(
            f"Remove the '{TOOLBAR_NAME}' toolbar" if on else
            f"Add a '{TOOLBAR_NAME}' toolbar with a button for this macro (all workbenches, "
            f"shortcut {TOOLBAR_SHORTCUT} if free)")

    def toggle_toolbar(self):
        try:
            if toolbar_installed():
                uninstall_toolbar()
                App.Console.PrintMessage(f"Live Section: '{TOOLBAR_NAME}' toolbar removed.\n")
            else:
                cmd, key = install_toolbar()
                note = f", shortcut {key}" if key else f" ({TOOLBAR_SHORTCUT} is taken, no shortcut)"
                App.Console.PrintMessage(f"Live Section: '{TOOLBAR_NAME}' toolbar added{note}.\n")
        except Exception as e:
            QMessageBox.warning(None, "Live Section", f"Could not change the toolbar: {e}")
        self._sync_toolbar_button()

    def show_panel(self):
        """Show the options in the Tasks panel (default) or as a dock window."""
        if PANEL_MODE == "task":
            try:
                if not Gui.Control.activeDialog():
                    self.btn_close.setVisible(False)
                    Gui.Control.showDialog(SectionTaskPanel(self, self.panel))
                    self._mode = "task"
                    return
                App.Console.PrintMessage(
                    "Another task dialog is open - showing the section panel as a window.\n"
                )
            except Exception as e:
                App.Console.PrintWarning(f"Tasks panel unavailable ({e}), using a window.\n")
        self.btn_close.setVisible(True)
        self._mode = "dock"
        self.setObjectName("LiveSectionAnalyzerDock")
        pm = _logo_pixmap()
        if pm is not None:
            self.setWindowIcon(QIcon(pm))
        self.panel.setMinimumWidth(PANEL_WIDTH)
        self.setWidget(self.panel)
        area = Qt.LeftDockWidgetArea if str(DOCK_AREA).lower() == "left" else Qt.RightDockWidgetArea
        mw = Gui.getMainWindow()
        mw.addDockWidget(area, self)
        self.show()
        # Otherwise the dock inherits whatever width its side of the window last had
        mw.resizeDocks([self], [PANEL_WIDTH], Qt.Horizontal)

    # ------------------------------------------------------------------
    # UI event handlers (cheap: they never do geometry work directly)
    # ------------------------------------------------------------------
    def schedule_update(self, *args):
        """Many events collapse into one update per timer interval."""
        if self._closed:
            return
        # Throttle (not restart): while the user keeps dragging, updates still
        # happen every interval instead of only after the movement stops.
        if not self._timer.isActive():
            self._timer.start()

    def _fill_list(self):
        self.obj_list.blockSignals(True)
        self.obj_list.clear()
        for t in self.targets:
            item = QListWidgetItem(t.label)
            item.setFlags(Qt.ItemIsUserCheckable | Qt.ItemIsEnabled)
            item.setCheckState(Qt.Checked if t.checked else Qt.Unchecked)
            item.setData(Qt.UserRole, t.key)
            pm = QPixmap(14, 14)
            r, g, b = (int(max(0.0, min(1.0, c)) * 255) for c in t.color[:3])
            pm.fill(QColor(r, g, b))
            item.setIcon(QIcon(pm))
            self.obj_list.addItem(item)
        self.obj_list.blockSignals(False)

    def on_target_toggled(self, item):
        if self._closed:
            return
        key = item.data(Qt.UserRole)
        for t in self.targets:
            if t.key == key:
                t.checked = item.checkState() == Qt.Checked
        self.schedule_update()

    def _check_all(self, flag):
        self.obj_list.blockSignals(True)
        for i in range(self.obj_list.count()):
            self.obj_list.item(i).setCheckState(Qt.Checked if flag else Qt.Unchecked)
        self.obj_list.blockSignals(False)
        for t in self.targets:
            t.checked = bool(flag)
        self.schedule_update()

    def on_slider_changed(self, value):
        """Slider -> spinbox (signals blocked to avoid the feedback loop)"""
        mapped_value = (value / 100.0) * self.offset_range
        self.offset_spin.blockSignals(True)
        self.offset_spin.setValue(mapped_value)
        self.offset_spin.blockSignals(False)
        self.schedule_update()

    def on_spin_changed(self, value):
        """Spinbox -> slider (signals blocked to avoid the feedback loop)"""
        slider_value = int((value / self.offset_range) * 100)
        slider_value = max(-100, min(100, slider_value))
        self.slider.blockSignals(True)
        self.slider.setValue(slider_value)
        self.slider.blockSignals(False)
        self.schedule_update()

    def _sync_slider(self):
        value = self.offset_spin.value()
        slider_value = int((value / self.offset_range) * 100)
        slider_value = max(-100, min(100, slider_value))
        self.slider.blockSignals(True)
        self.slider.setValue(slider_value)
        self.slider.blockSignals(False)

    # ------------------------------------------------------------------
    # Gizmo
    # ------------------------------------------------------------------
    def create_gizmo(self):
        try:
            view = Gui.ActiveDocument.ActiveView
            size = max(self.x_len, self.y_len, self.z_len) * 0.18
            self.gizmo = PlaneGizmo(view, size, self._gizmo_start, self._gizmo_drag, self._gizmo_end,
                                    self._rot_start, self._rot_drag, self._rot_end)
            self.gizmo.set_visible(self.chk_gizmo.isChecked())
        except Exception as e:
            App.Console.PrintWarning(f"Gizmo unavailable: {e}\n")
            self.gizmo = None
            self.chk_gizmo.setChecked(False)
            self.chk_gizmo.setEnabled(False)

    def on_gizmo_toggled(self, *args):
        if self.gizmo:
            self.gizmo.set_visible(self.chk_gizmo.isChecked())

    def plane_axes(self, plane_type):
        """In-plane axis u and half extents (along u and along w) of the current plane."""
        u, w = self._plane_frame[0], self._plane_frame[1]

        def half(v):
            return (abs(v.x) * self.x_len + abs(v.y) * self.y_len + abs(v.z) * self.z_len) / 2 * 1.1
        return u, half(u), half(w)

    def sync_gizmo(self, plane_type, normal, plane_base):
        if not self.gizmo or self.gizmo.dragging:
            return
        u, hu, hw = self.plane_axes(plane_type)
        self.gizmo.set_pose(plane_base, normal, u, getattr(self, "_plane_w0", None))
        self.gizmo.set_extents(hu, hw)

    def _gizmo_start(self):
        self._gizmo_dragging = True
        self._gizmo_start_offset = self.offset_spin.value()

    def _gizmo_drag(self, delta):
        """Called while dragging; returns the offset change actually applied."""
        off = self._gizmo_start_offset + delta
        off = max(-self.offset_range, min(self.offset_range, off))
        self.offset_spin.blockSignals(True)
        self.offset_spin.setValue(off)
        self.offset_spin.blockSignals(False)
        self._sync_slider()
        self.schedule_update()
        return self.offset_spin.value() - self._gizmo_start_offset

    def _rot_start(self, k):
        self._gizmo_dragging = True
        sp = (self.spin_tilt_a, self.spin_tilt_b)[k]
        self._rot_start_val = sp.value()

    def _rot_drag(self, k, deg):
        sp = (self.spin_tilt_a, self.spin_tilt_b)[k]
        sp.blockSignals(True)
        sp.setValue(max(sp.minimum(), min(sp.maximum(), self._rot_start_val + deg)))
        sp.blockSignals(False)
        self.schedule_update()

    def _rot_end(self):
        self._gizmo_dragging = False
        self.schedule_update()

    def _gizmo_end(self):
        self._gizmo_dragging = False
        self.schedule_update()          # full update (hatch etc.) after the drag

    def pick_color(self, button, target):
        """Open color picker dialog"""
        color_dialog = QColorDialog()
        color_dialog.setCurrentColor(button.palette().button().color())

        run = getattr(color_dialog, "exec_", None) or getattr(color_dialog, "exec")
        if run():
            color = color_dialog.currentColor()
            r, g, b = color.red() / 255.0, color.green() / 255.0, color.blue() / 255.0
            button.setStyleSheet(
                f"background-color: rgb({color.red()}, {color.green()}, {color.blue()}); max-width: 50px;"
            )

            if target == "edge":
                self.edge_feat.ViewObject.LineColor = (r, g, b)
            elif target == "hatch":
                self.hatch_feat.ViewObject.LineColor = (r, g, b)
            elif target == "fill":
                self.section_feat.ViewObject.ShapeColor = (r, g, b)
            self.update_style()
            if target == "fill":
                self.schedule_update()          # the mesh fill takes its color at update time

    # ------------------------------------------------------------------
    # Style-only updates (no geometry work)
    # ------------------------------------------------------------------
    @staticmethod
    def _set(vo, prop, value):
        """Assign a ViewObject property only if it actually changes."""
        if getattr(vo, prop) != value:
            setattr(vo, prop, value)

    def update_style(self, *args):
        if self._closed or not self.targets:
            return
        for t in self.targets:
            if t.bg_feat is not None:
                self._set(t.bg_feat.ViewObject, "Transparency", self.spin_trans.value())
        self._sync_clip_transparency(self.clip_ok and self.chk_gpu_clip.isChecked())
        self._set(self.edge_feat.ViewObject, "LineWidth", self.edge_width_spin.value())
        self._set(self.hatch_feat.ViewObject, "LineWidth", self.hatch_width_spin.value())
        self._set(self.hatch_feat.ViewObject, "PointSize", self.hatch_point_spin.value())
        self._apply_mesh_style()

    def _vis(self, feat, flag):
        self._set(feat.ViewObject, "Visibility", bool(flag))

    def _sync_clip_transparency(self, use_clip):
        """GPU clipping shows the originals, so the transparency goes on them directly.
        0 % leaves an object as the user made it."""
        trans = self.spin_trans.value()
        for t in self.targets:
            if use_clip and t.checked and trans > 0:
                self._apply_transparency(t, trans)
            else:
                self._restore_transparency(t)

    def _apply_transparency(self, t, trans):
        try:
            vo = t.obj.ViewObject
            if t.saved_look is None:
                t.saved_look = {p: getattr(vo, p) for p in ("Transparency", "ShapeAppearance", "DiffuseColor")
                                if hasattr(vo, p)}
            self._set(vo, "Transparency", trans)
        except Exception:
            pass

    def _restore_transparency(self, t):
        """Put back the object's own look, per-face colors included."""
        if t.saved_look is None:
            return
        look, t.saved_look = t.saved_look, None
        try:
            for prop, value in look.items():
                setattr(t.obj.ViewObject, prop, value)
        except Exception:
            pass

    def _release(self, t):
        """Remove a target's background copy and show the original again."""
        if t.bg_feat is not None:
            try:
                doc = t.bg_feat.Document
                if doc.getObject(t.bg_feat.Name):
                    doc.removeObject(t.bg_feat.Name)
            except Exception:
                pass
            t.bg_feat = None
            t.bg_mode = None
            try:
                t.obj.ViewObject.Visibility = t.was_visible
            except Exception:
                pass

    def _sync_targets(self, use_clip=False):
        """Create / remove the background copies so they match the checked list.
        Copies are only needed for the boolean cut; GPU clipping cuts the originals."""
        doc = App.ActiveDocument
        if not doc:
            return
        trans = self.spin_trans.value() if hasattr(self, "spin_trans") else 70
        self._sync_clip_transparency(use_clip)
        for t in self.targets:
            if use_clip:
                self._release(t)
            elif t.checked and t.bg_feat is None:
                t.was_visible = bool(t.obj.ViewObject.Visibility)
                feat = doc.addObject("Part::Feature", "Live_Section_Background")
                _hide_in_tree(feat)
                feat.ViewObject.ShapeColor = t.color
                feat.ViewObject.DisplayMode = "Shaded"
                feat.ViewObject.Transparency = trans
                feat.purgeTouched()
                t.bg_feat = feat
                t.bg_mode = None
            elif not t.checked and t.bg_feat is not None:
                self._release(t)



class _GeometryMixin:
    """Section plane, GPU clip, boolean cut and the exact (OpenCascade) section and hatch."""

    def _tilt_text(self):
        ta, tb = self.spin_tilt_a.value(), self.spin_tilt_b.value()
        if abs(ta) < 1e-9 and abs(tb) < 1e-9:
            return ""
        return "_tilt_%g_%g" % (ta, tb)

    def reset_tilt(self):
        for sp in (self.spin_tilt_a, self.spin_tilt_b):
            sp.blockSignals(True)
            sp.setValue(0.0)
            sp.blockSignals(False)
        self.schedule_update()

    def get_plane(self):
        """Returns (plane_type, normal, plane_base, center_pos).

        The plane goes through the bounding-box centre moved by `offset` along its normal.
        The tilt angles turn it about the two in-plane axes of the chosen base plane; the
        resulting in-plane frame is kept in self._plane_frame = (u, w, normal, d).
        """
        offset_val = self.offset_spin.value()
        c = self.bbox.Center
        ptype = self.combo_plane.currentText()
        if ptype == "YZ":
            n0, u0, w0 = App.Vector(1, 0, 0), App.Vector(0, 1, 0), App.Vector(0, 0, 1)
        elif ptype == "XZ":
            n0, u0, w0 = App.Vector(0, 1, 0), App.Vector(1, 0, 0), App.Vector(0, 0, 1)
        else:
            n0, u0, w0 = App.Vector(0, 0, 1), App.Vector(1, 0, 0), App.Vector(0, 1, 0)
        ta, tb = self.spin_tilt_a.value(), self.spin_tilt_b.value()
        names = {"YZ": ("Y", "Z"), "XZ": ("X", "Z"), "XY": ("X", "Y")}[ptype]
        self.lbl_tilt_a.setText("Tilt %s:" % names[0])
        self.lbl_tilt_b.setText("Tilt %s:" % names[1])
        n, u, w = App.Vector(n0), App.Vector(u0), App.Vector(w0)
        if abs(ta) > 1e-9 or abs(tb) > 1e-9:
            rot = App.Rotation(w0, tb).multiply(App.Rotation(u0, ta))
            n, u, w = rot.multVec(n0), rot.multVec(u0), rot.multVec(w0)
        plane_base = App.Vector(c.x + n.x * offset_val, c.y + n.y * offset_val, c.z + n.z * offset_val)
        self._plane_w0 = w0
        self._plane_frame = (u, w, n, n.dot(plane_base))
        center_pos = plane_base.dot(n0)                      # position along the base axis
        return ptype, n, plane_base, center_pos

    def set_clip(self, normal, plane_base, flip=False):
        """Position the GPU clip plane (cheap). flip=True keeps the other half."""
        d = normal.dot(plane_base)
        n = App.Vector(normal)
        if CLIP_KEEP_NEGATIVE != bool(flip):
            n = App.Vector(-n.x, -n.y, -n.z)
            d = -d
        self.clip.plane.setValue(coin.SbPlane(coin.SbVec3f(n.x, n.y, n.z), d))

    def compute_cut_solid(self, shape, plane_type, normal, plane_base, flip=False):
        """Exact boolean cut (slow). Used when GPU clipping is off and for freezing.

        flip=True keeps the opposite half. The geometry itself is never moved
        or reflected, so the object stays where it is while the plane moves.
        """
        size = max(self.x_len, self.y_len, self.z_len) * 4
        cutter = Part.makeBox(size, size, size)
        # local +Z is the plane normal; the cutter removes the +normal side,
        # or the -normal side when flipped
        cutter.translate(App.Vector(-size / 2, -size / 2, -size if flip else 0))

        rot = App.Rotation(App.Vector(0, 0, 1), normal)         # local +Z -> plane normal
        cutter.Placement = App.Placement(plane_base, rot).multiply(cutter.Placement)
        return shape.cut(cutter)

    @staticmethod
    def _plane_hits_bbox(bb, n, d):
        """False when the plane n.x = d cannot touch the bounding box (cheap test)."""
        c = bb.Center
        r = (bb.XLength * abs(n.x) + bb.YLength * abs(n.y) + bb.ZLength * abs(n.z)) * 0.5
        tol = max(bb.DiagonalLength, 1.0) * 1e-6
        return abs(n.x * c.x + n.y * c.y + n.z * c.z - d) <= r + tol

    @staticmethod
    def _nkey(n):
        return (round(n.x, 5), round(n.y, 5), round(n.z, 5))

    def _slice_cached(self, t, plane_type, normal, plane_base):
        return (t.key, plane_type, self._nkey(normal), round(normal.dot(plane_base), 4)) in self._slice_cache

    def get_slice(self, t, plane_type, normal, plane_base):
        """Section wires of one object via Shape.slice (cached)."""
        d = normal.dot(plane_base)
        if not self._plane_hits_bbox(t.bbox, normal, d):
            self._skipped += 1
            return []
        key = (t.key, plane_type, self._nkey(normal), round(d, 4))
        wires = self._slice_cache.get(key)
        if wires is None:
            t0 = time.perf_counter()
            try:
                wires = t.shape.slice(normal, d)
            except Exception as e:
                App.Console.PrintWarning(f"Slice failed: {e}\n")
                wires = []
            t.slice_ms = (time.perf_counter() - t0) * 1e3
            if len(self._slice_cache) >= SLICE_CACHE_SIZE:
                self._slice_cache.pop(next(iter(self._slice_cache)))
            self._slice_cache[key] = wires
        return wires

    @staticmethod
    def make_faces(wires):
        """Build faces (with holes) from the slice wires."""
        if not wires:
            return []
        try:
            f = Part.makeFace(wires, "Part::FaceMakerBullseye")
            faces = f.Faces
            if faces:
                return faces
        except Exception:
            pass
        faces = []
        for w in wires:
            try:
                if w.isClosed():
                    faces.append(Part.Face(w))
            except Exception:
                pass
        return faces

    @staticmethod
    def _pt(plane_type, c, u, v):
        if plane_type == "YZ":
            return App.Vector(c, u, v)
        if plane_type == "XZ":
            return App.Vector(u, c, v)
        return App.Vector(u, v, c)

    def build_hatch(self, faces, plane_type, center_pos, spacing, angle=45.0):
        """Hatch of one set of section faces with a SINGLE boolean.

        The lines run at `angle` degrees (in-plane axes as in _pt) and sit at multiples of
        `spacing` from the origin, exactly like the mesh section draws them.
        """
        section = Part.Compound(faces)
        bb = section.BoundBox
        U, W, N, d = self._plane_frame
        corners = [App.Vector(x, y, z) for x in (bb.XMin, bb.XMax)
                   for y in (bb.YMin, bb.YMax) for z in (bb.ZMin, bb.ZMax)]
        us = [c.dot(U) for c in corners]
        vs = [c.dot(W) for c in corners]
        u_min, u_max, v_min, v_max = min(us) - 2, max(us) + 2, min(vs) - 2, max(vs) + 2
        origin = N * d

        def pt(u, v):
            return origin + U * u + W * v

        a = math.radians(angle)
        nu, nv = math.cos(a), math.sin(a)             # line normal
        wu, wv = -nv, nu                              # line direction
        s_vals = [u * nu + v * nv for u in (u_min, u_max) for v in (v_min, v_max)]
        s_lo, s_hi = min(s_vals), max(s_vals)
        if (s_hi - s_lo) / spacing > MAX_HATCH_LINES:
            spacing = (s_hi - s_lo) / MAX_HATCH_LINES
            App.Console.PrintWarning(
                "Hatch spacing too small for this section, spacing increased automatically.\n"
            )
        half = math.hypot(u_max - u_min, v_max - v_min) / 2 + 1.0
        t0 = (u_min + u_max) / 2 * wu + (v_min + v_max) / 2 * wv   # centre along the lines

        lines = []
        j = math.ceil(s_lo / spacing)
        while j * spacing <= s_hi:
            s = j * spacing
            bu, bv = s * nu + t0 * wu, s * nv + t0 * wv
            lines.append(Part.makeLine(
                pt(bu - half * wu, bv - half * wv),
                pt(bu + half * wu, bv + half * wv)))
            j += 1

        if not lines:
            return None

        try:
            result = section.common(Part.Compound(lines))
            if result.Edges:
                return result
        except Exception as e:
            App.Console.PrintWarning(f"Hatch failed: {e}\n")
        return None

    def build_hatch_per_object(self, per_obj, plane_type, center_pos, spacing):
        """Hatch of all sectioned objects, each with its own angle / spacing (HATCH_STYLES)."""
        parts = []
        for t, faces in per_obj:
            angle, scale = self._hatch_style(t)
            h = self.build_hatch(faces, plane_type, center_pos, spacing * scale, angle)
            if h is not None:
                parts.append(h)
        return Part.Compound(parts) if parts else None



class _MeshSectionMixin:
    """Mesh-based section drawn as Coin nodes (uses the numpy core)."""

    def _create_preview_node(self):
        """Coin node for the fast drag outline. It sits before the clip plane, so it is
        never clipped (it lies exactly in the plane)."""
        if not HAS_NP:
            return
        try:
            sw = coin.SoSwitch()
            sw.whichChild.setValue(coin.SO_SWITCH_NONE)
            sep = coin.SoSeparator()
            lm = coin.SoLightModel()
            lm.model.setValue(coin.SoLightModel.BASE_COLOR)
            col = coin.SoBaseColor()
            col.rgb.setValue(0.0, 0.0, 0.0)
            ds = coin.SoDrawStyle()
            ds.lineWidth.setValue(2.0)
            coords = coin.SoCoordinate3()
            lines = coin.SoLineSet()
            for node in (lm, col, ds, coords, lines):
                sep.addChild(node)
            sw.addChild(sep)
            self.clip_parent.insertChild(sw, 0)
            self.preview, self.preview_switch = sep, sw
            self.preview_coords, self.preview_lines = coords, lines
        except Exception as e:
            App.Console.PrintWarning(f"Fast preview unavailable: {e}\n")
            self.preview = None

    def _create_mesh_nodes(self):
        """Coin nodes of the mesh-based section: fill (polygons), outline and hatch (lines).

        Like the fast preview they sit before the clip plane, so they are never clipped.
        """
        if not HAS_NP:
            return
        try:
            sw = coin.SoSwitch()
            sw.whichChild.setValue(coin.SO_SWITCH_NONE)
            root = coin.SoSeparator()
            lm = coin.SoLightModel()
            lm.model.setValue(coin.SoLightModel.BASE_COLOR)
            root.addChild(lm)

            # fill: concave polygons (holes are bridged in), one color per polygon;
            # pushed back a little so the lines drawn in the same plane stay on top
            fsep = coin.SoSeparator()
            offs = coin.SoPolygonOffset()
            offs.factor.setValue(1.0)
            offs.units.setValue(1.0)
            bind = coin.SoMaterialBinding()
            bind.value.setValue(coin.SoMaterialBinding.PER_PART)
            fcol = coin.SoBaseColor()
            hints = coin.SoShapeHints()
            hints.vertexOrdering.setValue(coin.SoShapeHints.UNKNOWN_ORDERING)
            hints.shapeType.setValue(coin.SoShapeHints.UNKNOWN_SHAPE_TYPE)
            hints.faceType.setValue(coin.SoShapeHints.UNKNOWN_FACE_TYPE)
            fcoords = coin.SoCoordinate3()
            fset = coin.SoFaceSet()
            for node in (offs, bind, fcol, hints, fcoords, fset):
                fsep.addChild(node)
            root.addChild(fsep)

            def line_group():
                sep = coin.SoSeparator()
                col = coin.SoBaseColor()
                ds = coin.SoDrawStyle()
                coords = coin.SoCoordinate3()
                lines = coin.SoLineSet()
                for node in (col, ds, coords, lines):
                    sep.addChild(node)
                root.addChild(sep)
                return col, ds, coords, lines

            ecol, eds, ecoords, elines = line_group()
            hcol, hds, hcoords, hlines = line_group()
            sw.addChild(root)
            self.clip_parent.insertChild(sw, 0)
            self.mesh_switch = sw
            self.mesh_nodes = {
                "fill": (fcol, fcoords, fset),
                "edge": (ecol, eds, ecoords, elines),
                "hatch": (hcol, hds, hcoords, hlines),
            }
        except Exception as e:
            App.Console.PrintWarning(f"Mesh section unavailable: {e}\n")
            self.mesh_switch = None
            self.mesh_nodes = None

    @staticmethod
    def _tessellation(t):
        """Vertices / triangles of the object as numpy arrays (built once)."""
        if t.mesh is None:
            tol = max(t.bbox.DiagonalLength * 1e-3, 1e-4)
            verts, tris = t.shape.tessellate(tol)
            t.mesh = (np.array([(v.x, v.y, v.z) for v in verts], dtype=float).reshape(-1, 3),
                      np.array(tris, dtype=np.int64).reshape(-1, 3))
        return t.mesh

    def mesh_segments(self, t, normal, d):
        """Intersection of the plane n.x = d with the tessellation: (k, 2, 3) segments."""
        V, T = self._tessellation(t)
        if len(T) == 0:
            return np.zeros((0, 2, 3))
        n = np.array((normal.x, normal.y, normal.z))
        sv = V @ n - d
        pos = sv[T] >= 0.0                              # (m, 3)
        cnt = pos.sum(axis=1)
        cut = (cnt == 1) | (cnt == 2)
        if not cut.any():
            return np.zeros((0, 2, 3))
        P, sp, c1 = T[cut], pos[cut], (cnt[cut] == 1)
        lone = np.where(c1, sp.argmax(axis=1), (~sp).argmax(axis=1))
        r = np.arange(len(P))
        ia, ib, ic = P[r, lone], P[r, (lone + 1) % 3], P[r, (lone + 2) % 3]
        sa = sv[ia]

        def cross(i_other):
            so = sv[i_other]
            f = (sa / (sa - so))[:, None]
            return V[ia] + f * (V[i_other] - V[ia])

        return np.stack((cross(ib), cross(ic)), axis=1)

    # ------------------------------------------------------------------
    # Mesh-based section (v0.5.0)
    # ------------------------------------------------------------------
    @staticmethod
    def _plane_basis(plane_type):
        """In-plane axes (u, w) of the section plane as numpy vectors."""
        if plane_type == "YZ":
            return np.array((0.0, 1.0, 0.0)), np.array((0.0, 0.0, 1.0))
        if plane_type == "XZ":
            return np.array((1.0, 0.0, 0.0)), np.array((0.0, 0.0, 1.0))
        return np.array((1.0, 0.0, 0.0)), np.array((0.0, 1.0, 0.0))

    def _basis_for(self, plane_type):
        """Current in-plane axes (u, w) as numpy vectors, tilt included."""
        fr = getattr(self, "_plane_frame", None)
        if fr is None:
            return self._plane_basis(plane_type)
        return (np.array((fr[0].x, fr[0].y, fr[0].z)), np.array((fr[1].x, fr[1].y, fr[1].z)))

    def _mesh_active(self):
        return (HAS_NP and self.mesh_switch is not None and hasattr(self, "chk_mesh")
                and self.chk_mesh.isChecked())

    def _mesh_for(self, t, fine):
        """Welded tessellation (V, T, gap) of a target, coarse or fine; built once and cached."""
        lvl = 1 if fine else 0
        m = t.meshes.get(lvl)
        if m is None and fine:
            coarse = self._mesh_for(t, False)
            if (len(coarse[1]) > MESH_FINE_MAX_TRIS
                    or getattr(t, "mesh_s", 0.0) * MESH_FINE_PREDICT > MESH_FINE_BUDGET_S
                    or time.perf_counter() - self._mesh_t0 > MESH_FINE_BUDGET_S):
                t.meshes[1] = coarse                  # heavy part / out of time: keep the coarse mesh
                return coarse
        if m is None:
            diag = max(t.bbox.DiagonalLength, 1e-9)
            tol = max(diag * (MESH_TOL_FINE_REL if fine else MESH_TOL_REL), MESH_TOL_MIN)
            t_tess = time.perf_counter()
            Vs, Ts, Ss, off = [], [], [], 0
            for i, solid in enumerate(t.shape.Solids or [t.shape]):
                verts, tris = solid.tessellate(tol)
                if not tris:
                    continue
                Vs.append(np.array([(p.x, p.y, p.z) for p in verts], dtype=float).reshape(-1, 3))
                Ts.append(np.array(tris, dtype=np.int64).reshape(-1, 3) + off)
                Ss.append(np.full(len(verts), i, dtype=np.int64))
                off += len(verts)
            if Vs:
                V, T = mesh_weld(np.concatenate(Vs), np.concatenate(Ts), np.concatenate(Ss), diag * 1e-6)
            else:
                V, T = np.zeros((0, 3)), np.zeros((0, 3), dtype=np.int64)
            m = (V, T, diag * 1e-4)
            t.meshes[lvl] = m
            if not fine:
                t.mesh_s = time.perf_counter() - t_tess        # cost of the coarse mesh, predicts the fine one
        return m

    def _mesh_loops(self, t, fine, normal, d):
        """(closed, open) section polylines of one object from its mesh (cached)."""
        key = (t.key, fine, round(normal.x, 6), round(normal.y, 6), round(normal.z, 6), round(d, 4))
        hit = self._loop_cache.get(key)
        if hit is None:
            V, T, gap = self._mesh_for(t, fine)
            n = (normal.x, normal.y, normal.z)
            hit = mesh_section_loops(V, T, np.array(n), d, gap, self._plane_index(t, fine, V, T, n))
            if len(self._loop_cache) >= MESH_CACHE_SIZE:
                self._loop_cache.pop(next(iter(self._loop_cache)))
            self._loop_cache[key] = hit
        return hit

    @staticmethod
    def _plane_index(t, fine, V, T, n):
        """Slab index of a big mesh once the same normal is used twice in a row: moving the
        plane reuses it, while tilting (a new normal every update) stays a plain scan."""
        if len(T) < MESH_INDEX_MIN_TRIS:
            return None
        nkey = tuple(round(c, 6) for c in n)
        entry = t.plane_index.get(fine)
        if entry is None or entry[0] is not V or entry[1] != nkey:
            t.plane_index[fine] = (V, nkey, None)
            return None
        if entry[2] is None:
            entry = (V, nkey, mesh_plane_index(V, T, n))
            t.plane_index[fine] = entry
        return entry[2]

    def _fill_quads(self, key, loops):
        """Convex quads of the section fill (cached); see fill_trapezoids()."""
        quads = self._tri_cache.get(key)
        if quads is None:
            quads = fill_trapezoids(loops)
            if len(self._tri_cache) >= MESH_CACHE_SIZE:
                self._tri_cache.pop(next(iter(self._tri_cache)))
            self._tri_cache[key] = quads
        return quads

    def _hatch_style(self, t):
        """(angle, spacing factor) of an object; stable for the whole session."""
        idx = self._hatch_idx.get(t.key)
        if idx is None:
            idx = len(self._hatch_idx)
            self._hatch_idx[t.key] = idx
        return HATCH_STYLES[idx % len(HATCH_STYLES)]

    @staticmethod
    def _fill_node(coords, shape_set, arrays):
        """Point arrays ((n, 3) each) -> SoCoordinate3 + numVertices of a line/face set."""
        if arrays:
            pts = np.concatenate(arrays)
            counts = [len(a) for a in arrays]
            coords.point.setValues(0, len(pts), pts.tolist())
            shape_set.numVertices.setValues(0, len(counts), counts)
        coords.point.setNum(sum(len(a) for a in arrays))
        shape_set.numVertices.setNum(len(arrays))

    def _apply_mesh_style(self):
        """Colors and widths of the mesh section follow the panel (via the exact features)."""
        if self.mesh_nodes is None:
            return
        try:
            ecol, eds, _, _ = self.mesh_nodes["edge"]
            hcol, hds, _, _ = self.mesh_nodes["hatch"]
            ecol.rgb.setValue(*tuple(self.edge_feat.ViewObject.LineColor[:3]))
            eds.lineWidth.setValue(float(self.edge_feat.ViewObject.LineWidth))
            hcol.rgb.setValue(*tuple(self.hatch_feat.ViewObject.LineColor[:3]))
            hds.lineWidth.setValue(float(self.hatch_feat.ViewObject.LineWidth))
        except Exception:
            pass

    def _mesh_hide(self):
        if self.mesh_switch is not None:
            self.mesh_switch.whichChild.setValue(coin.SO_SWITCH_NONE)

    def _update_mesh_section(self, active, plane_type, normal, plane_base, pose, quick, tm):
        """Outline, hatch and fill of the checked objects from their tessellation.

        Loops come from chaining the plane/triangle segments, the hatch is scanline-clipped
        against them (even-odd) and the fill is one polygon per outer loop with its holes
        bridged in. Everything is drawn as Coin nodes; exact geometry exists only for Freeze.
        """
        perf = time.perf_counter
        d = normal.dot(plane_base)
        U, W = self._basis_for(plane_type)
        basis = np.stack((U, W), axis=1)                                   # (3, 2)
        base3 = np.array((normal.x, normal.y, normal.z)) * d + np.array(
            (pose.Base.x, pose.Base.y, pose.Base.z))

        def to3(p2):
            return p2 @ basis.T + base3

        fine = not quick
        spacing = self.spin_spacing.value()
        want_fill = self.chk_section_fill.isChecked()
        want_edges = self.chk_edges.isChecked()
        want_hatch = self.chk_hatch.isChecked() and (fine or MESH_DRAG_HATCH)
        obj_colors = self.chk_obj_colors.isChecked()
        flat = tuple(self.section_feat.ViewObject.ShapeColor[:3])

        edges, hatch, fill, fill_cols, fill_counts = [], [], [], [], []
        self._mesh_t0 = perf()
        for t in active:
            if not self._plane_hits_bbox(t.bbox, normal, d):
                self._skipped += 1
                continue
            t0 = perf()
            closed, opened = self._mesh_loops(t, fine, normal, d)
            tm["slice"] += perf() - t0
            if not closed and not opened:
                continue

            loops = [L @ basis for L in closed]                            # (m, 2) in-plane
            if want_edges:
                t0 = perf()
                for L in loops:
                    edges.append(to3(np.vstack((L, L[:1]))))
                for L in opened:
                    edges.append(to3(L @ basis))
                tm["edges"] += perf() - t0

            if want_fill and loops:
                t0 = perf()
                npts = sum(len(L) for L in loops)
                shade = tuple(c * 0.75 for c in t.color[:3]) if obj_colors else flat
                if npts <= MESH_MAX_FILL_POINTS:
                    if npts <= MESH_MAX_QUAD_POINTS:
                        tkey = (t.key, fine, round(normal.x, 6), round(normal.y, 6), round(normal.z, 6), round(d, 4))
                        quads = self._fill_quads(tkey, loops)             # convex quads: no tearing
                        if len(quads):
                            fill.append(to3(quads.reshape(-1, 2)))        # one transform for all quads
                            fill_counts.extend([4] * len(quads))
                            fill_cols.extend([shade] * len(quads))
                    else:
                        for p in fill_polygons(loops):                    # huge sections
                            fill.append(to3(p))
                            fill_counts.append(len(p))
                            fill_cols.append(shade)
                tm["faces"] += perf() - t0

            if want_hatch and loops:
                t0 = perf()
                angle, scale = self._hatch_style(t)
                segs = hatch_segments(loops, angle, spacing * scale, MAX_HATCH_LINES)
                if len(segs):
                    hatch.append(to3(segs.reshape(-1, 2)))
                tm["hatch"] += perf() - t0

        t0 = perf()
        try:
            fcol, fcoords, fset = self.mesh_nodes["fill"]
            if fill:
                fpts = np.concatenate(fill)
                fcoords.point.setValues(0, len(fpts), fpts.tolist())
                fset.numVertices.setValues(0, len(fill_counts), fill_counts)
            fcoords.point.setNum(sum(len(a) for a in fill))
            fset.numVertices.setNum(len(fill_counts))
            if fill_cols:
                fcol.rgb.setValues(0, len(fill_cols), fill_cols)
            fcol.rgb.setNum(len(fill_cols))
            self._fill_node(self.mesh_nodes["edge"][2], self.mesh_nodes["edge"][3], edges)
            hcoords, hlines = self.mesh_nodes["hatch"][2:]
            if hatch:
                pts = np.concatenate(hatch)
                hcoords.point.setValues(0, len(pts), pts.tolist())
                hlines.numVertices.setValues(0, len(pts) // 2, [2] * (len(pts) // 2))
                hcoords.point.setNum(len(pts))
                hlines.numVertices.setNum(len(pts) // 2)
            else:
                hcoords.point.setNum(0)
                hlines.numVertices.setNum(0)
            shown = bool(fill or edges or hatch)
            self.mesh_switch.whichChild.setValue(coin.SO_SWITCH_ALL if shown else coin.SO_SWITCH_NONE)
        except Exception as e:
            App.Console.PrintError(f"Mesh section error: {e}\n")
        tm["fill"] += perf() - t0

    def _show_preview(self, segs):
        """Draw the fast outline (list of (k,2,3) arrays) or hide it when empty."""
        if self.preview is None:
            return
        pts = [a for a in segs if len(a)]
        if not pts:
            self.preview_switch.whichChild.setValue(coin.SO_SWITCH_NONE)
            return
        arr = np.concatenate(pts).reshape(-1, 3)
        k = len(arr) // 2
        # setValues() does not shrink the fields: cut them to the new size, otherwise
        # the segments of earlier plane positions stay on screen
        self.preview_coords.point.setValues(0, len(arr), arr.tolist())
        self.preview_coords.point.setNum(len(arr))
        self.preview_lines.numVertices.setValues(0, k, [2] * k)
        self.preview_lines.numVertices.setNum(k)
        self.preview_switch.whichChild.setValue(coin.SO_SWITCH_ALL)



class _FreezeMixin:
    """Freeze Section: copies the current section into static objects."""

    # ------------------------------------------------------------------
    # Freeze
    # ------------------------------------------------------------------
    @staticmethod
    def _has_shape(feat):
        return feat is not None and feat.Shape is not None and not feat.Shape.isNull()

    def freeze_section(self):
        """Freeze current section view using SimpleCopy with folder"""
        doc = App.ActiveDocument
        if not doc or not any(t.checked for t in self.targets):
            return

        progress = None
        try:
            progress = QProgressDialog("Freezing section ...", None, 0, 0, Gui.getMainWindow())
            progress.setWindowTitle("Live Section Analyzer")
            progress.setWindowModality(Qt.WindowModal)
            progress.setMinimumDuration(0)
            progress.setCancelButton(None)
            progress.show()
            QApplication.processEvents()
        except Exception:
            progress = None
        try:
            # Make sure everything is up to date (including hatch)
            self._timer.stop()
            self.update_section(force_exact=True)      # real geometry, even in mesh mode

            plane_type, normal, plane_base, center_pos = self.get_plane()
            offset_val = self.offset_spin.value()

            tilt = self._tilt_text()
            group_name = f"Frozen_Section_{plane_type}{tilt}_Offset_{offset_val:.1f}"

            # Delete old frozen group
            if self.frozen_group and doc.getObject(self.frozen_group.Name):
                for obj in list(self.frozen_group.Group):
                    try:
                        doc.removeObject(obj.Name)
                    except Exception:
                        pass
                try:
                    doc.removeObject(self.frozen_group.Name)
                except Exception:
                    pass

            self.frozen_group = doc.addObject("App::DocumentObjectGroup", group_name)
            self.frozen_group.Label = f"Frozen Section ({plane_type}{tilt.replace('_', ' ')}, Offset: {offset_val:.1f} mm)"

            copied_objects = []

            # 1. Background of every sectioned object: always a real boolean cut
            #    here, because the live GPU clip does not change the geometry.
            for t in self.targets:
                if not t.checked:
                    continue
                bg_shape = self.compute_cut_solid(
                    t.shape, plane_type, normal, plane_base, self.chk_mirror_bg.isChecked()
                )
                if bg_shape is not None and not bg_shape.isNull():
                    bg_copy = doc.addObject("Part::Feature", f"Section_Background_{plane_type}")
                    bg_copy.Label = f"{t.label} ({plane_type})"
                    bg_copy.Shape = bg_shape
                    bg_copy.ViewObject.ShapeColor = t.color
                    bg_copy.ViewObject.DisplayMode = "Shaded"
                    bg_copy.ViewObject.Transparency = self.spin_trans.value()
                    copied_objects.append(bg_copy)

            # 2. Section fill
            if self.section_feat.ViewObject.Visibility and self._has_shape(self.section_feat):
                fill_copy = doc.addObject("Part::Feature", f"Section_Fill_{plane_type}")
                fill_copy.Shape = self.section_feat.Shape
                fill_copy.Placement = self.section_feat.Placement
                fill_copy.ViewObject.ShapeColor = self.section_feat.ViewObject.ShapeColor
                fill_copy.ViewObject.DiffuseColor = self.section_feat.ViewObject.DiffuseColor
                fill_copy.ViewObject.LineColor = self.section_feat.ViewObject.LineColor
                fill_copy.ViewObject.LineWidth = self.section_feat.ViewObject.LineWidth
                fill_copy.ViewObject.DisplayMode = "Shaded"
                fill_copy.ViewObject.Transparency = 0
                copied_objects.append(fill_copy)

            # 3. Edge lines
            if self.edge_feat.ViewObject.Visibility and self._has_shape(self.edge_feat):
                edge_copy = doc.addObject("Part::Feature", f"Section_Edges_{plane_type}")
                edge_copy.Shape = self.edge_feat.Shape
                edge_copy.Placement = self.edge_feat.Placement
                edge_copy.ViewObject.LineColor = self.edge_feat.ViewObject.LineColor
                edge_copy.ViewObject.LineWidth = self.edge_feat.ViewObject.LineWidth
                edge_copy.ViewObject.DisplayMode = "Wireframe"
                edge_copy.ViewObject.PointSize = 1
                copied_objects.append(edge_copy)

            # 4. Hatch lines
            if self.hatch_feat.ViewObject.Visibility and self._has_shape(self.hatch_feat):
                hatch_copy = doc.addObject("Part::Feature", f"Section_Hatch_{plane_type}")
                hatch_copy.Shape = self.hatch_feat.Shape
                hatch_copy.Placement = self.hatch_feat.Placement
                hatch_copy.ViewObject.LineColor = self.hatch_feat.ViewObject.LineColor
                hatch_copy.ViewObject.LineWidth = self.hatch_feat.ViewObject.LineWidth
                hatch_copy.ViewObject.DisplayMode = "Wireframe"
                hatch_copy.ViewObject.PointSize = self.hatch_point_spin.value()
                copied_objects.append(hatch_copy)

            if not copied_objects:
                if progress is not None:
                    progress.close()
                QMessageBox.warning(None, "Warning", "No section elements found to copy!")
                try:
                    doc.removeObject(self.frozen_group.Name)
                except Exception:
                    pass
                self.frozen_group = None
                return

            for obj in copied_objects:
                self.frozen_group.addObject(obj)

            self.frozen_group.ViewObject.Visibility = True

            Gui.Selection.clearSelection()
            Gui.Selection.addSelection(self.frozen_group)

            for obj in copied_objects:
                obj.purgeTouched()
            self.frozen_group.purgeTouched()

            if progress is not None:
                progress.close()
            QMessageBox.information(
                None,
                "Success",
                f"Section successfully frozen!\n"
                f"Group name: {self.frozen_group.Label}\n"
                f"Element count: {len(copied_objects)}\n"
                f"Plane: {plane_type}, Offset: {offset_val:.1f} mm\n\n"
                f"📁 Contents:\n" +
                "\n".join([f"  • {obj.Label}" for obj in copied_objects])
            )

        except Exception as e:
            App.Console.PrintError(f"Freeze Error: {str(e)}\n")
            QMessageBox.critical(None, "Error", f"Error while freezing section:\n{str(e)}")
        finally:
            if progress is not None:
                progress.close()
            self.schedule_update()                     # back to the live (mesh or exact) view



class LiveSectionAnalyzer(_SceneMixin, _PanelMixin, _GeometryMixin, _MeshSectionMixin, _FreezeMixin,
                          QDockWidget):
    def __init__(self):
        super().__init__()
        self.setWindowTitle("Interactive Section Analysis")
        self.setAllowedAreas(Qt.LeftDockWidgetArea | Qt.RightDockWidgetArea)

        self._closed = False
        self._mode = None             # "task" or "dock"
        self.panel = None
        self.targets = []             # all listed objects (checked = sectioned)
        self.section_feat = None
        self.edge_feat = None
        self.hatch_feat = None
        self.frozen_group = None
        self.clip = None
        self.clip_parent = None
        self.clip_ok = False
        self.preview = None
        self.mesh_switch = None       # Coin nodes of the mesh-based section (see _create_mesh_nodes)
        self.mesh_nodes = None
        self.gizmo = None
        self._gizmo_dragging = False
        self._gizmo_start_offset = 0.0
        self._slice_cache = {}
        self._loop_cache = {}         # mesh section loops per (object, mesh level, plane)
        self._tri_cache = {}          # OpenCascade triangulation of the section fill (same keys)
        self._hatch_idx = {}          # object key -> index into HATCH_STYLES
        self._scene_dirty = False     # a placement / shape changed in the document
        self._observer = None
        self._doc_name = App.ActiveDocument.Name if App.ActiveDocument else None
        self.init_done = False

        if not self._collect_targets():
            self._closed = True
            return

        # Plane center follows the selected objects; ranges follow the whole scene
        picked = [t.shape for t in self.targets if t.checked] or [t.shape for t in self.targets]
        self.bbox = self._union_bbox(picked)
        scene = self._union_bbox([t.shape for t in self.targets])
        self.x_len = scene.XMax - scene.XMin
        self.y_len = scene.YMax - scene.YMin
        self.z_len = scene.ZMax - scene.ZMin

        self._skipped = 0
        # Debounce timer: many UI events -> a single update
        self._timer = QTimer(self)
        self._timer.setSingleShot(True)
        self._timer.setInterval(60)
        self._timer.timeout.connect(self.update_section)
        # One full (fine) update after parts stop moving
        self._settle_timer = QTimer(self)
        self._settle_timer.setSingleShot(True)
        self._settle_timer.setInterval(SCENE_SETTLE_MS)
        self._settle_timer.timeout.connect(self.update_section)

        # Features first: init_ui() needs to know whether GPU clipping is available
        self.create_features()
        self.init_ui()
        self.create_gizmo()
        self.update_style()
        self.update_section()
        self.init_done = True
        self._observer = _SceneObserver(self)
        App.addDocumentObserver(self._observer)
        self.show_panel()

    def create_features(self):
        """Create all features once"""
        doc = App.ActiveDocument
        if not doc:
            return

        # Section fill
        self.section_feat = doc.addObject("Part::Feature", "Live_Section_Fill")
        self.section_feat.ViewObject.ShapeColor = (0.75, 0.65, 0.68)
        self.section_feat.ViewObject.LineColor = (0.0, 0.0, 0.0)
        self.section_feat.ViewObject.LineWidth = 3.0
        self.section_feat.ViewObject.DisplayMode = "Shaded"
        self.section_feat.ViewObject.Transparency = 0
        self.section_feat.ViewObject.Visibility = False

        # Section edge lines
        self.edge_feat = doc.addObject("Part::Feature", "Live_Section_Edges")
        self.edge_feat.ViewObject.LineColor = (0.0, 0.0, 0.0)
        self.edge_feat.ViewObject.LineWidth = 2.0
        self.edge_feat.ViewObject.DisplayMode = "Wireframe"
        self.edge_feat.ViewObject.Visibility = False
        self.edge_feat.ViewObject.PointSize = 1

        # Hatch lines
        self.hatch_feat = doc.addObject("Part::Feature", "Live_Hatch_Lines")
        self.hatch_feat.ViewObject.LineColor = (0.3, 0.3, 0.3)
        self.hatch_feat.ViewObject.LineWidth = 1.0
        self.hatch_feat.ViewObject.DisplayMode = "Wireframe"
        self.hatch_feat.ViewObject.Visibility = False
        self.hatch_feat.ViewObject.PointSize = 1

        # One GPU clip plane at the root of the 3D view clips EVERYTHING that is shown
        if HAS_COIN:
            try:
                self.clip = coin.SoClipPlane()
                self.clip.on.setValue(False)
                view = Gui.ActiveDocument.ActiveView
                self.clip_parent = PlaneGizmo._render_group(view.getSceneGraph())
                self.clip_parent.insertChild(self.clip, 0)
                self.clip_ok = True
                self._create_preview_node()
                self._create_mesh_nodes()
            except Exception as e:
                App.Console.PrintWarning(f"Clip plane unavailable, using boolean mode: {e}\n")
                self.clip = None
                self.clip_parent = None
                self.clip_ok = False

        for feat in (self.section_feat, self.edge_feat, self.hatch_feat):
            _hide_in_tree(feat)
            feat.purgeTouched()

    # ------------------------------------------------------------------
    # Main update
    # ------------------------------------------------------------------
    def _overlay_pose(self, normal, flip, use_clip):
        """Offset of the in-plane overlays (see OVERLAY_OFFSET_REL)."""
        eps = max(self.x_len, self.y_len, self.z_len) * OVERLAY_OFFSET_REL
        keep = App.Vector(normal)
        if CLIP_KEEP_NEGATIVE != bool(flip):
            keep = App.Vector(-keep.x, -keep.y, -keep.z)    # side that stays visible
        # clip mode: just inside the kept half; boolean mode: just in front of the cut face
        return App.Placement(keep * (eps if use_clip else -eps), App.Rotation())

    def update_section(self, force_exact=False):
        if self._closed or not self.targets:
            return
        doc = App.ActiveDocument
        if not doc:
            return

        self._timer.stop()
        t_start = time.perf_counter()
        tm = {"slice": 0.0, "faces": 0.0, "fill": 0.0, "edges": 0.0, "hatch": 0.0, "bg": 0.0}
        self._skipped = 0
        self._meshed = 0
        self._mesh_t0 = time.perf_counter()

        # While dragging the slider we only do the cheap parts
        quick = self.slider.isSliderDown() or self._gizmo_dragging

        if self._scene_dirty:
            self._scene_dirty = False
            if self._refresh_targets():
                quick = True                    # parts are moving: coarse now, fine when they stop
                self._settle_timer.start()

        use_clip = self.clip_ok and self.chk_gpu_clip.isChecked()
        self._sync_targets(use_clip)
        active = [t for t in self.targets if t.checked]
        busy = not quick                                   # wait cursor for the full (slow) update
        if busy:
            QApplication.setOverrideCursor(Qt.WaitCursor)

        plane_type, normal, plane_base, center_pos = self.get_plane()
        flip = self.chk_mirror_bg.isChecked()
        pose = self._overlay_pose(normal, flip, use_clip)
        # force_exact: Freeze needs the real OpenCascade geometry
        mesh_mode = self._mesh_active() and not force_exact

        self.sync_gizmo(plane_type, normal, plane_base)

        try:
            # --- CLIP: the whole scene (GPU mode) ---
            if use_clip:
                self.set_clip(normal, plane_base, flip)
                self.clip.on.setValue(True)
            elif self.clip_ok:
                self.clip.on.setValue(False)

            # --- BACKGROUND copies of the sectioned objects ---
            t0 = time.perf_counter()
            # GPU mode needs no copies: the clip plane cuts the original objects,
            # which stay selectable (Assembly joints, measuring, ...).
            for t in (() if use_clip else active):
                self._vis(t.obj, False)
                if t.bg_mode is None or not quick:
                    # (while dragging in boolean mode the previous solid is kept)
                    t.bg_feat.Shape = self.compute_cut_solid(t.shape, plane_type, normal, plane_base, flip)
                    self._set(t.bg_feat.ViewObject, "Lighting", "Two side")
                    t.bg_mode = "solid"
                self._vis(t.bg_feat, True)

            tm["bg"] = time.perf_counter() - t0
            self._meshed = 0

            if mesh_mode:
                # --- SECTION from the tessellation: outline, hatch and fill are Coin nodes ---
                self._show_preview([])
                for feat in (self.section_feat, self.edge_feat, self.hatch_feat):
                    self._vis(feat, False)
                self._update_mesh_section(active, plane_type, normal, plane_base, pose, quick, tm)
            else:
                self._mesh_hide()
                # --- SECTION (slice) of every checked object ---
                wires, faces, face_colors = [], [], []
                per_obj = []                                   # (target, faces) for the hatch
                preview_segs = []
                for t in active:
                    t0 = time.perf_counter()
                    if (quick and self.preview is not None and t.slice_ms > FAST_PREVIEW_MS
                            and not self._slice_cached(t, plane_type, normal, plane_base)):
                        # expensive object while dragging: outline from the tessellation
                        if self._plane_hits_bbox(t.bbox, normal, normal.dot(plane_base)):
                            preview_segs.append(self.mesh_segments(t, normal, normal.dot(plane_base)))
                            self._meshed += 1
                        else:
                            self._skipped += 1
                        tm["slice"] += time.perf_counter() - t0
                        continue
                    w = self.get_slice(t, plane_type, normal, plane_base)
                    tm["slice"] += time.perf_counter() - t0
                    if not w:
                        continue
                    t0 = time.perf_counter()
                    f = self.make_faces(w)
                    tm["faces"] += time.perf_counter() - t0
                    wires += w
                    faces += f
                    if f:
                        per_obj.append((t, f))
                    shade = tuple(c * 0.75 for c in t.color[:3])
                    face_colors += [shade + (1.0,)] * len(f)

                self._show_preview(preview_segs)

                if not wires:
                    self._vis(self.section_feat, False)
                    self._vis(self.edge_feat, False)
                    self._vis(self.hatch_feat, False)
                else:
                    # Fill
                    t0 = time.perf_counter()
                    if self.chk_section_fill.isChecked() and faces:
                        self.section_feat.Shape = Part.Compound(faces)
                        self.section_feat.Placement = pose
                        vo = self.section_feat.ViewObject
                        if self.chk_obj_colors.isChecked() and len(faces) == len(face_colors):
                            vo.DiffuseColor = face_colors
                        else:
                            vo.DiffuseColor = [tuple(vo.ShapeColor[:3]) + (1.0,)]
                        self._vis(self.section_feat, True)
                    else:
                        self._vis(self.section_feat, False)

                    tm["fill"] = time.perf_counter() - t0

                    # Edge lines
                    t0 = time.perf_counter()
                    if self.chk_edges.isChecked():
                        self.edge_feat.Shape = Part.Compound(wires)
                        self.edge_feat.Placement = pose
                        self._vis(self.edge_feat, True)
                    else:
                        self._vis(self.edge_feat, False)

                    tm["edges"] = time.perf_counter() - t0

                    # Hatch (skipped while dragging)
                    t0 = time.perf_counter()
                    if self.chk_hatch.isChecked() and faces and not quick:
                        hatch = self.build_hatch_per_object(
                            per_obj, plane_type, center_pos, self.spin_spacing.value())
                        if hatch is not None:
                            self.hatch_feat.Shape = hatch
                            self.hatch_feat.Placement = pose
                            self._vis(self.hatch_feat, True)
                        else:
                            self._vis(self.hatch_feat, False)
                    else:
                        self._vis(self.hatch_feat, False)
                    tm["hatch"] = time.perf_counter() - t0

            self.update_style()

        except Exception as e:
            App.Console.PrintError(f"Section Error: {str(e)}\n")

        if busy:
            QApplication.restoreOverrideCursor()

        # Plain Part::Feature objects need no recompute; just clear the "touched" flag.
        for feat in [self.section_feat, self.edge_feat, self.hatch_feat] + [t.bg_feat for t in active]:
            if feat is not None:
                feat.purgeTouched()

        total = time.perf_counter() - t_start
        # adaptive delay: after a slow update give the UI more time to collect events
        self._timer.setInterval(int(min(250, max(16 if quick else 60, total * 300))))

        if DEBUG_TIMING:
            App.Console.PrintMessage(
                "[LSA] %s %d obj (%d skipped by bbox, %d mesh) | bg %.0f  slice %.0f  faces %.0f  "
                "fill %.0f  edges %.0f  hatch %.0f | total %.0f ms\n" % (
                    ("drag" if quick else "full") + ("/mesh" if mesh_mode else ""),
                    len(active), self._skipped, self._meshed,
                    tm["bg"] * 1e3, tm["slice"] * 1e3, tm["faces"] * 1e3,
                    tm["fill"] * 1e3, tm["edges"] * 1e3, tm["hatch"] * 1e3, total * 1e3))

    # ------------------------------------------------------------------
    # Cleanup
    # ------------------------------------------------------------------
    def shutdown(self, close_dialog=True):
        """Remove everything the macro created. Safe to call more than once."""
        if self._closed:
            return
        self._closed = True

        if self._mode == "task" and close_dialog:
            try:
                Gui.Control.closeDialog()
            except Exception:
                pass

        try:
            self._timer.stop()
            self._settle_timer.stop()
        except Exception:
            pass
        if self._observer is not None:
            try:
                App.removeDocumentObserver(self._observer)
            except Exception:
                pass
            self._observer = None

        if self.gizmo is not None:
            self.gizmo.remove()
            self.gizmo = None

        if self.preview is not None and self.clip_parent is not None:
            try:
                self.clip_parent.removeChild(self.preview_switch)
            except Exception:
                pass
            self.preview = None

        if self.mesh_switch is not None and self.clip_parent is not None:
            try:
                self.clip_parent.removeChild(self.mesh_switch)
            except Exception:
                pass
            self.mesh_switch = None
            self.mesh_nodes = None

        # Remove clip plane from the scene graph before deleting its owner
        if self.clip is not None and self.clip_parent is not None:
            try:
                self.clip_parent.removeChild(self.clip)
            except Exception:
                pass
            self.clip = None
            self.clip_parent = None

        # Show the original objects again and remove their copies
        for t in self.targets:
            self._restore_transparency(t)
            self._release(t)

        doc = App.ActiveDocument
        if doc:
            # Delete all live features (frozen group is kept)
            for feat in [self.section_feat, self.edge_feat, self.hatch_feat]:
                if feat is not None:
                    try:
                        if doc.getObject(feat.Name):
                            doc.removeObject(feat.Name)
                    except Exception:
                        pass

        self._slice_cache.clear()
        self._loop_cache.clear()
        self._tri_cache.clear()

        if self._mode == "task":
            # The Tasks panel owns the form; the unused dock can simply go.
            self.deleteLater()

    def on_document_closed(self):
        """The sectioned document is going away: the panel has nothing left to show."""
        self._timer.stop()
        self._settle_timer.stop()
        # Not from inside the document's own deletion
        QTimer.singleShot(0, self.shutdown if self._mode == "task" else self.close)

    def closeEvent(self, event):
        """Dock-window close (also used when the macro is started again)"""
        self.shutdown()
        super().closeEvent(event)

        # Fully remove the dock so repeated runs don't leave hidden docks behind
        try:
            Gui.getMainWindow().removeDockWidget(self)
            self.deleteLater()
        except Exception:
            pass


# Run the macro
try:
    section_analyzer.close()
except Exception:
    pass

section_analyzer = LiveSectionAnalyzer()
